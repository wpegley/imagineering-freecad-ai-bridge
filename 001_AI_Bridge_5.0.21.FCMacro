# -*- coding: utf-8 -*-
__Version__ = '5.0.21'
"""
FreeCAD AI Bridge - Industrial Grade Edition
Author: Imagineering (built with Claude Code)
Version: 5.0.21 - Imagineering Edition (Ollama / Local AI)
Date: 2026-11-11

CHANGES IN v3.4.6 (2026-11-01) - ONE BAD COMMAND NO LONGER WEDGES THE BRIDGE:
======================================
Observed live on FreeCAD 26.3: the reader sat 2035 bytes behind with
last_position frozen at 372, commands_processed 0 and errors_count 0 - while
monitoring_active stayed true and the heartbeat kept ticking every few
seconds. Every health signal said the bridge was fine. It answered nothing,
including a plain 'hello'.

Two cooperating defects caused that, and neither reported itself:

  1. The outer handler in process_ai_commands() deliberately left
     _state.last_position alone on a fatal error ("Don't update position on
     fatal errors"). The offending bytes therefore stayed at the head of the
     queue forever.
  2. The mtime gate committed _state._last_input_mtime BEFORE the file had
     been read successfully. So after a failure, this revision of the input
     was already marked "seen": later polls returned early, and when a new
     write finally bumped the mtime, the reader seeked back to the same
     frozen position and hit the same bad bytes again.

Together: a single unprocessable command permanently silenced the channel
with every status field still reading healthy.

  - The fatal path now skips past the bytes it could not process, says how
    many it dropped, and sets error_state so the condition is visible.
    Dropping pending input is a real cost; being unreachable with a healthy
    heartbeat is a worse one.
  - The mtime is now committed only after a pass that actually completed.

ALSO: _ConsoleCapture.start() has never worked on any current build.
App.Console.AddObserver does not exist on FreeCAD 1.1 or 26.3 - verified,
dir(App.Console) has GetObservers and no AddObserver on both - so the bare
"except Exception: self._observer = None" has always been taken and stop()
has always returned empty lists. Every 'report_view' this bridge has ever
returned was silently empty. It now records WHY and reports
capture_unavailable, instead of handing back an empty capture that reads as
"the command produced no output".

NOT a bridge defect, recorded here so it is not re-chased: a run_macro that
failed with "name 'getString' is not defined" was a bug in the CALLED macro
plus a real bug in FreeCAD 26.3's bundled pivy - Mod/pivy/coin.py:754 has
"return getString().__iter__()" missing its "self.", so ANY iteration or
"x in name" test on an SbName raises NameError. Wrap getName() in str().
The bridge reported that error correctly.

CHANGES IN v3.4.5 (2026-08-23) - THE CONFIG NO LONGER FAILS SILENTLY:
======================================
get_ai_io_dir() and get_learning_dir() both read ai_bridge_config.json with a
bare open() - no encoding argument at all - and swallowed every failure into a
warning plus a fall-through to the default.

A BOM on that file, which PowerShell's Set-Content writes by DEFAULT, therefore
moved the operator's IO directory back to the default without the bridge
stopping or the operator being told anything that reads as an error. Everything
downstream then wrote to a channel nobody had chosen.

This is the same defect GIMP 0.1.0 shipped, where a BOM on its config silently
unwatched the remote inbox for hours while ping and info both answered healthy.
See HQ/41_AI_Bridge/10_Core/RESILIENCE_CONTRACT_0.0.01.md: repair what is
provably safe, fail loudly otherwise, never degrade to defaults.

Both loaders now go through resilience.load_json_repairing when 10_Core is
reachable. A BOM is repaired, damage needing a guess is refused loudly, and the
defaults are used only when the file genuinely does not exist. The import
degrades exactly the way the wire import above it does, for the same reason:
this macro runs inside FreeCAD and must never fail to load over a path problem.

MAJOR CHANGES IN v3.4.4 (2026-08-21) - WIRE 2 / AI REDUNDANCY:
======================================
Emits the shared wire-2 envelope defined in
HQ/41_AI_Bridge/10_Core/WIRE_CONTRACT_0.0.01.md, so this bridge can be driven
by any AI through an IDE rather than only by one vendor's assistant.

Why this mattered here more than anywhere else: measured across 549 real lines
of this bridge's outbox, NOT ONE carried an "id" at any level a generic reader
inspects. The correlation id lived at content.command_id, success was a bool at
content.success, and the payload was nested under "content". A language model
coped by reading the stdout and inferring which request a result answered. No
CLI, MCP server or local Ollama model can do that -- so in practice this bridge
was unusable by anything except a model clever enough to paper over it.

- write_output() and flush_result_buffer() now pass every entry through
  _conform(), which calls the shared wire.upgrade().
- The wire import is SOFT here, unlike the other five bridges which assert:
  this macro runs inside FreeCAD and must not be taken down by a path problem.
  It degrades to wire 1 plus client-side normalisation.
- No verb, GUI or sandbox behaviour changed.

MAJOR CHANGES IN v3.4.3 (2026-07-25) - RETRIEVAL FIX (PHASE 4 TUNING):
======================================
  * ROOT CAUSE FOUND: TechDataReviewer.search_knowledge() tests
    `query_lower in category.lower()` - it substring-matches the WHOLE query
    against category/key names. 'box' matches; 'create a 10mm box with a hole'
    matches NOTHING. v3.4.0-3.4.2 passed the raw user prompt straight in, so
    knowledge retrieval returned ZERO hits for every realistic request. The
    thin ~300-token context was not under-tuned, it was empty of retrieved
    knowledge. The KB was never consulted in practice.
  * extract_query_terms(): tokenises the prompt, drops stopwords (including
    'make'/'create', which match every constructor and rank nothing), and
    expands through a FreeCAD domain alias map - users say "hole", the KB
    indexes "cut"/"boolean".
  * retrieve_patterns(): searches PER TERM, merges, dedupes, and ranks by
    distinct term coverage (whole-word matches score double) instead of
    taking whatever came back first.
  * _format_hit(): compact one-line rendering replaces json.dumps(indent=1),
    which was burning 3-5x the tokens for identical information.
  * recent_successes() is now RELEVANCE-ranked, not pure recency - it took the
    last five verified commands regardless of whether they related to the
    request. Recency remains the fallback when nothing scores.
  * NEW "Context" button + describe_last_build(): shows the search terms used,
    hits found vs included, token split, and whether pattern selection fell
    back to recency. Rebuilds against whatever is in the prompt box, so
    retrieval can be tested WITHOUT spending a generation. A thin context is
    now diagnosable instead of mysterious.
  * stable_hash() updated for the new (text, report) return signature; it
    hashes the prompt-independent verified set so registration stays stable.

MAJOR CHANGES IN v3.4.2 (2026-07-25) - LOCAL-CHAT MESSAGING FIX:
======================================
  * BUG (mine, from 3.4.1): selecting Ollama and pressing Open Chat launched
    the panel correctly but then showed the EDITOR success dialog - "opened
    with AI Bridge Workspace / will automatically read .windsurfrules". Every
    line of that was false for Ollama. The rules_map lookup had no 'ollama'
    entry and fell through to a hardcoded '.windsurfrules' default.
  * open_ide_with_context() now branches on is_local_chat BEFORE doing any
    editor work: no IDE instruction file is generated, no workspace is synced,
    and the dialog states what actually happens - knowledge is INJECTED into
    the system prompt per message, with the live token count shown, and the
    model cannot browse files the way Claude Code can.
  * rules_map: 'windsurf' -> 'devin' ('.devin/', legacy .windsurfrules still
    honoured), 'claude-code' added, and the silent '.windsurfrules' fallback
    replaced with an honest generic string. That default was the root cause.

MAJOR CHANGES IN v3.4.1 (2026-07-25) - NAMING + GUI PLACEMENT + DEVIN FIX:
======================================
  [NAMING CORRECTION]
  * "Hermes" is GONE. It was a poor choice: Hermes is a MODEL that runs
    inside Ollama (NousResearch Hermes), so using it as the name of the
    panel that connects TO Ollama implied you were running Hermes when you
    were actually running qwen3-coder. Everything is now named for what it
    is: Ollama. agent_id changed from "hermes" to "ollama".
    NOTE: learning-database entries tagged source_agent "hermes" from a
    v3.4.0 session keep that tag and stay unverified - harmless, but they
    will show as a separate agent in get_provenance_stats().

  [GUI PLACEMENT]
  * The standalone "Ollama" button is removed. Ollama is now an entry in
    the existing IDE dropdown, so ONE selector answers ONE question:
    where does my AI come from? Selecting it changes the launch button
    from "Open IDE" to "Open Chat" and opens the local chat panel.
    Ollama is not an editor - there is no application to launch - so it is
    routed inside launch_ide() before the install-detection check.

  [DEVIN DESKTOP - EXTERNAL BREAKING CHANGE, NOT OURS]
  * Cognition rebranded Windsurf to Devin Desktop on 2026-06-02 via an OTA
    update; the Windows binary is now Devin.exe. The old 'windsurf' CLI
    probe therefore reported "Not Found" on any machine that had simply
    updated. The 'windsurf' entry is replaced by 'devin', detection gained
    a cli_alt fallback list so legacy installs still resolve, and a saved
    preference of 'windsurf' migrates silently to 'devin'.

MAJOR CHANGES IN v3.4.0 (2026-07-25) - OLLAMA INTEGRATION, PHASES 1-10:
======================================
  SCOPE: This release lands the *foundation* only - Config, provider-agnostic
  LLM client, threaded worker, and a minimal chat panel. It deliberately does
  NOT submit anything to the bridge yet (that is Phase 5). The goal of this
  build is to prove that a 20-60 second local model generation CANNOT stall
  the FreeCAD GUI. Everything here is additive; set
  Config.OLLAMA_ENABLED = False to disable the entire feature path and get
  v3.3.3 behaviour back.

  [PHASE 1 - CONFIG]
  * New OLLAMA_* block in Config. num_ctx is set EXPLICITLY -
    Ollama defaults to 4096 and truncates SILENTLY, which would eat the
    injected knowledge base without any warning in the logs.

  [PHASE 2 - LLMClient]
  * Provider-agnostic client (Ollama local + OpenRouter cloud) over stdlib
    urllib - no new dependencies inside FreeCAD's Python.
  * Streaming for both wire formats: Ollama NDJSON (/api/chat) and
    OpenAI-style SSE (/v1/chat/completions).
  * ensure_server_running() starts `ollama serve` on demand so Ollama does
    not need to autostart and squat on RAM.

  [PHASE 3 - THREADING (the whole point of this release)]
  * OllamaWorker(QThread): network I/O ONLY. It never touches App, Gui,
    the document, or App.Console - FreeCAD's API is not thread-safe and this
    boundary is absolute. Results cross back via Qt signals, which Qt queues
    onto the GUI thread for us.
  * _ollama_generating global is separate from _executing_command so the
    v3.3.3 watchdog does not misreport a long generation as a GUI freeze.
  * OllamaChatDialog carries a LIVE HEARTBEAT (100ms QTimer spinner). If the
    GUI thread ever blocks, the spinner visibly stops - that is the
    acceptance test for this phase, not a benchmark score.

  [DELIBERATELY NOT IN THIS BUILD]
  * No bridge submission, no code extraction, no auto-repair loop, no
    provenance tagging, no registration handshake. Phases 4-10.

MAJOR CHANGES IN v3.3.3 (2026-07-12) - GUI-FREEZE HARDENING:
======================================
  * Root-caused a hard GUI lockup: Bridge commands execute synchronously on the
    FreeCAD GUI thread, so any long op (heavy Coin3D shadow render, big recompute,
    infinite loop) froze the whole app with no watchdog. FreeCAD's API is not
    thread-safe, so we CANNOT move exec off the GUI thread; instead:
  * Removed all time.sleep() calls from the GUI thread (file-lock retry + 50ms
    batch delay) - locked input file no longer micro-stalls the UI.
  * Added a background daemon WATCHDOG thread that keeps running while the GUI is
    blocked (GIL releases during OCCT calls). It observes _executing_command and,
    if a command holds the GUI thread past Config.WATCHDOG_WARN_SEC, writes a
    diagnostic to the error log + ai_watchdog.json naming the freeze. Philosophy
    (Rule 42): DETECT, WARN, NEVER BLOCK. It cannot kill a frozen command, but a
    freeze is now logged instead of a silent mystery. COMMAND_TIMEOUT_SEC repurposed.

MAJOR CHANGES IN v3.3.2 (2026-07-06):
======================================
  * Heading now uses the standard GradientLogoLabel (QPainter green->cyan->
    blue gradient, reference impl from 150_Ladder_Safety) instead of
    flat-colour HTML spans; "AI Bridge" as cyan subtitle beneath.

MAJOR CHANGES IN v3.3.1 (2026-07-06):
======================================
[REBRAND POLISH]:
  * Filename drops "Hardened" -> 001_AI_Bridge_v3.3.1.FCMacro.
  * GUI heading is just "Imagineering AI Bridge" (version lives in the
    window title / TTS / console, all from Config.VERSION).
  * Quick Capture + Auto-Synthesize buttons removed - technique capture
    is automatic; the group is now a passive "Technique Knowledge" status.
  * Remaining off-palette colours corrected to the Macro_Training Rule-12
    scheme (activity monitor, log, Connect/Disconnect/Open IDE buttons,
    description text).

MAJOR CHANGES IN v3.3.0 (2026-07-06):
======================================
[IMAGINEERING GUI REBRAND]:
  * All user-facing version strings now derive from Config.VERSION (the
    spoken TTS startup said "3.0" and the GUI title said "3.1.1" while the
    actual version was 3.2.0 — no string carries its own version anymore).
  * "Community Knowledge Edition" branding removed.
  * Decorative emojis removed from the GUI (brain/camera/books etc.) for
    the clean Imagineering presentation style; dialog restyled to the
    standard palette (#1e1e2e bg, cyan/green accents).
  * "Browse Knowledge" button + handler removed — the Bridge does the
    knowledge lifting itself; no manual folder browsing required.

MAJOR CHANGES IN v3.2.0 (see Config.VERSION history):
======================================
  * Self-learning wired: common_mistakes + command_templates now populate;
    both surfaced in the AI context summary.

MAJOR CHANGES IN v3.1.1 (2026-03-18):
======================================
[FULL AUDIT — 7 bugs fixed, 2 features added]:
  * CRITICAL FIX: Self-heal queue detection counted ALL lines in input file
    instead of only unprocessed lines after last_position. This caused false
    "stagnant" triggers after ~6 commands, wiping the entire queue and dropping
    commands. Now reads only from current_position forward.
  * HIGH FIX: Duplicate hash detection used 5-minute window (not 2-sec as
    documented). Legitimate repeated commands (recompute, fitAll) were silently
    dropped. Reduced to 30-second window.
  * MEDIUM FIX: agent_id was missing from non-execute responses (ping, query,
    correct_command). Multi-AI result filtering via read_result() would timeout
    for these command types. All 7 response types now include agent_id.
  * MEDIUM FIX: importlib.import_module('sys') bypassed the security sandbox.
    AST validator now checks importlib.import_module() calls for blocked modules.
    Also added ast.ImportFrom check ('from os import path' was not caught).
  * LOW FIX: Processed command ID eviction used set→list which has no ordering.
    Now tracks insertion order via _processed_id_order list for true FIFO.
  * LOW FIX: Removed dead code is_duplicate_by_content() (defined, never called).
  * NEW: run_macro command type — AI agents can execute .FCMacro files safely
    without triggering exec()/open() sandbox blocks. Path-validated to only allow
    files under Macro_Directory or FreeCAD AppData.
  * NEW: Active document check on bridge connect — warns in Report View if no
    document is open, so AI agents know to create one first.

MAJOR CHANGES IN v3.1.0 (2026-03-13):
======================================
[MULTI-IDE SUPPORT - Universal AI Bridge]:
  * NEW: IDEManager class - auto-detects installed IDEs (VS Code, Windsurf, Cursor, Zed)
  * NEW: IDE selector dropdown in GUI replaces single "VS Code" button
  * NEW: "Open IDE" button launches whichever IDE is selected
  * NEW: Universal context file generator works with any IDE's AI assistant
  * NEW: Startup instructions are now IDE-agnostic (not VS Code specific)
  * NEW: Standalone bridge helper script for terminal-only workflows
  * NEW: IDE preference saved to config (remembers last used IDE)
  * Windsurf support via 'windsurf' CLI command
  * Cursor support via 'cursor' CLI command
  * Zed support via 'zed' CLI command
  * Auto-detection checks PATH and common install locations
  * Graceful fallback if selected IDE not installed
  * Context instructions updated for Windsurf Cascade / Cursor AI / generic assistants

MAJOR CHANGES IN v3.0.9 (2026-01-25):
======================================
[ADVANCED STARTUP TEST SUITE - 32 Tests]:
  * Expanded from 16 basic tests to 32 comprehensive tests
  * Tests derived from Technical_Data learning resources:
    - Part_Scripting_Reference.txt (900 lines of FreeCAD Part API)
    - Expressions_Reference.txt (mathematical functions)
    - FreeCAD_Knowledge_Base.json (285 patterns)
  * CATEGORY 1: Core Infrastructure (8 tests)
    - Basic execution, error handling, security blocking, I/O, learning system
  * CATEGORY 2: Part Module Geometry (8 tests)
    - Part.makeBox with vertex/edge/face validation
    - Part.makeSphere with surface area calculation (4πr²)
    - Part.makeCylinder with volume validation (πr²h)
    - Boolean Fuse/Cut operations with volume checks
    - Wire→Face creation from vectors
    - Face→Solid extrusion
    - BSpline curve creation (advanced geometry)
  * CATEGORY 3: Knowledge Base & Learning (6 tests)
    - AI documentation files (7 required docs)
    - FreeCAD_Knowledge_Base.json integrity (285 patterns)
    - Community_Knowledge directory structure
    - Error→Fix Tracker functionality
    - Learning database read/write
    - TechDataReviewer search capability
  * CATEGORY 4: Advanced Transformations (6 tests)
    - Shape translation with center-of-mass verification
    - Shape rotation (45° around Z-axis with trig validation)
    - Shape scaling with volume ratio (2³ = 8x volume)
    - BoundBox analysis
    - Center of Mass calculation
    - Compound shape creation
  * CATEGORY 5: Infrastructure (4 tests)
    - AI directories, monitor timer, health check, executor
  * Results grouped by category with visual status
  * Detailed failure reporting for debugging

MAJOR CHANGES IN v3.0.8 (2026-01-25):
======================================
[ERROR→FIX AUTOMATIC LEARNING]:
  * NEW: ErrorFixTracker class - tracks errors awaiting AI fixes
  * When AI sends a command that fails, the error is stored
  * When the NEXT command succeeds with similar structure, it's detected as a fix
  * The error→fix pair is automatically recorded in learning database
  * Uses similarity analysis (40-95% keyword overlap = likely correction)
  * Special detection for "has no attribute" errors (tracks bad attribute removal)
  * Generates human-readable solution descriptions automatically
  * Console feedback: "[LEARNED] Error→Fix pair recorded!"
  * 2-minute timeout for stale errors (prevents false matches)
  * Closes the learning loop: Error → AI Fix → Automatic Knowledge Update

MAJOR CHANGES IN v3.0.6 (2025-12-04):
======================================
[FEEDBACK LOOP COMPLETION - CRITICAL FIXES]:
  * search_for_error() now searches ALL 9 knowledge bases (was only 2)
  * FreeCAD_Knowledge_Base.json (250 patterns) - NOW SEARCHED
  * Python_Patterns_Index.json (112 patterns) - NOW SEARCHED
  * FreeCAD_Workbenches_Knowledge_Base.json (120+ workbenches) - NOW SEARCHED
  * Enhanced keyword extraction from error messages (extracts names, attributes)
  * Success reporting now includes ALL commands (even None results)
  * NEW: 'correct_command' API - AI can now correct failed commands in-place
  * Corrections automatically recorded in learning database
  * Full audit report: Technical_Data/AI_BRIDGE_FEEDBACK_LOOP_AUDIT_2025-12-04.md

MAJOR CHANGES IN v3.0.3 (2025-12-02):
======================================
[AI FEEDBACK LOOP - CRITICAL ENHANCEMENT]:
  * write_comprehensive_report_for_ai() - AI agent now receives detailed feedback
  * Command results automatically written to output file with full context
  * Error reports include learning database suggestions
  * Error reports include technical documentation references
  * Fix suggestions generated automatically from error type
  * TechDataReviewer.search_for_error() - searches docs for error keywords
  * Closes the feedback loop: AI → Command → Result → AI (complete cycle)
  * Enables true self-correction without manual error reporting

MAJOR CHANGES IN v3.0.2 (2025-12-01):
======================================
[SELF-LEARNING SYSTEM]:
  * Technical Data folder review on startup
  * Automatic loading of FreeCAD_Knowledge_Base.json
  * Expressions_Reference.txt integration
  * Python_Scripting_Conventions.txt integration
  * Quick pattern lookup for common operations
  * Search capability across all technical resources

[SELF-IMPROVING SYSTEM]:
  * Pattern recognition from successful commands
  * Learning database updates from usage
  * AI context summary generation with latest patterns
  * Automatic knowledge base expansion

[SELF-HEALING SYSTEM]:
  * Automatic file system integrity checks
  * Missing file auto-recreation
  * File permission auto-repair
  * Large output file auto-rotation
  * Database corruption auto-recovery
  * Memory cleanup for processed command IDs
  * Health checks every 30 seconds

MAJOR CHANGES IN v3.0.1 (2025-12-01):
======================================
[DUPLICATE COMMAND PREVENTION]:
  * Added content-based deduplication (MD5 hash with 2-second window)
  * Immediate ID marking with forced file system flush
  * Post-processing 50ms delay to prevent rapid-fire duplicates
  * Command timestamp tracking to detect same command < 2 seconds
  * Enhanced logging for duplicate detection
  * Updated macro count documentation (43 → 46 macros)

MAJOR CHANGES IN v3.0:
======================
[SECURITY HARDENING]:
  * Command sandboxing with whitelist validation
  * Path traversal protection
  * Input sanitization and validation
  * Command timeout protection (30s default)
  * Restricted execution environment

[RELIABILITY IMPROVEMENTS]:
  * Automatic timer crash recovery
  * File position corruption protection
  * Buffer flush timer properly started
  * Thread-safe database operations
  * Atomic status file updates
  * Database backup before writes

[MONITORING & DIAGNOSTICS]:
  * Performance metrics tracking
  * Health check endpoint
  * Comprehensive error logging
  * System resource monitoring
  * Alert system for anomalies

[OPERATIONAL IMPROVEMENTS]:
  * Graceful shutdown handling
  * File rotation for large outputs
  * Configurable portable paths
  * Configuration versioning
  * Comprehensive self-tests

This macro enables console logging and provides AI agent I/O capabilities with GUI configuration.
DESIGNED FOR CONTINUOUS OPERATION - keeps FreeCAD GUI open with AI monitoring active.

FREECAD PYTHON DOCUMENTATION & RESOURCES FOR AI AGENTS:
============================================================

OFFICIAL DOCUMENTATION:
- FreeCAD Python API: https://freecad.github.io/SourceDoc/
- Python Scripting Tutorial: https://wiki.freecad.org/Python_scripting_tutorial
- Power Users Hub: https://wiki.freecad.org/Power_users_hub
- FreeCAD API Reference: https://wiki.freecad.org/FreeCAD_API

ESSENTIAL MODULES:
- App (FreeCAD): Document, objects, geometry operations
- Gui (FreeCADGui): View operations, selection, GUI interaction
- Part: CAD modeling, shapes, boolean operations
- Draft: 2D drafting tools
- Sketcher: Constraint-based sketching

COMMON PATTERNS:
- Create document: App.newDocument('Name')
- Add object: App.ActiveDocument.addObject('Type', 'Name')
- Access selection: Gui.Selection.getSelection()
- Recompute: App.ActiveDocument.recompute()

BEST PRACTICES:
1. Always check App.ActiveDocument exists before operations
2. Use try/except for error handling
3. Call recompute() after geometry changes
4. Access objects by Name, not Label (Label can have duplicates)
5. Check object.isDerivedFrom('Type') before type-specific operations

LEARNING RESOURCES:
- FreeCAD Forum: https://forum.freecad.org/
- Python Console (built-in): View -> Panels -> Python console
- Macro Recorder: Macro -> Macro recording -> Record actions
- Example Macros: https://wiki.freecad.org/Macros_recipes

3D MODEL LIBRARY RESOURCES (AI REFERENCE):
============================================================
The AI Bridge provides context about indexed 3D model libraries at startup.

RESOURCE FILES (Machine-Readable):
- 3D_Library_Resources.json: Complete reference for 3D library system
  * Database location and schema
  * External sources (FreeCAD Library, GrabCAD, Thingiverse, McMaster-Carr)
  * Supported formats (FCStd, STEP, STL, BREP)
  * Search capabilities and AI usage patterns
  * Access macros: 047_3D_Library_Indexer, 048_3D_Library_Browser

DATABASE LOCATION:
- Windows: %APPDATA%\\FreeCAD\\3d_library_index.db
- Linux/Mac: ~/.FreeCAD/3d_library_index.db

AI USAGE PATTERN:
1. Check if database exists on startup
2. Reference 3D_Library_Resources.json for capabilities
3. When user needs parts: Suggest 048_3D_Library_Browser
4. When user needs to index: Suggest 047_3D_Library_Indexer
5. Can query database directly using Python sqlite3 if needed

NOTE: These are REFERENCE resources. AI should not create/modify library
      macros or database unless explicitly requested by the user.
"""

__Name__ = 'AI Bridge - Self-Learning & Self-Healing'
__Comment__ = 'The AI Bridge: lets an external AI agent drive this FreeCAD session over a JSONL command channel, with a live activity view, learning store and local Ollama support'
__Author__ = 'Imagineering'
__Version__ = '5.0.21'
__Date__ = '2026-11-11'
__License__ = 'MIT'
__Web__ = ''
__Wiki__ = ''
__Icon__ = ''
__Help__ = 'Run this macro to enable AI Bridge with self-learning and self-healing features.'
__Status__ = 'Production'
__Requires__ = 'FreeCAD >= v0.17'
__Communication__ = ''
__Files__ = ''

import FreeCAD as App
import FreeCADGui as Gui
import os
import sys
import ast
import re
import threading
import queue
import time
import shutil
import traceback
import atexit
from datetime import datetime, timedelta
from collections import deque
import glob
import json
import subprocess
# v3.4.0: stdlib HTTP for the Ollama / OpenRouter client. Deliberately NOT
# `requests` - no third-party packages get pushed into FreeCAD's Python.
import urllib.request
import urllib.error
# v3.5.0: for the Rule 12 Support & Donation block, which draws its icons
# from embedded SVG and opens the donation pages in the system browser.
import base64
import webbrowser

# ============================================================
# REDIRECT __pycache__ TO TECHNICAL_DATA FOLDER
# ============================================================
# Keep Macro_Loader folder clean - redirect Python bytecode cache
# to Technical_Data/__pycache__/ instead of creating it in Macro_Loader
_pycache_dir = os.path.join(
    os.path.dirname(os.path.dirname(os.path.abspath(__file__))),
    'Macro_03', 'Technical_Data', '__pycache__'
)
if not os.path.exists(_pycache_dir):
    try:
        os.makedirs(_pycache_dir, exist_ok=True)
    except:
        pass
# Python 3.8+ supports sys.pycache_prefix
if hasattr(sys, 'pycache_prefix'):
    sys.pycache_prefix = _pycache_dir

# ============================================================
# TEXT-TO-SPEECH INTEGRATION
# ============================================================

class TextToSpeech:
    """Windows Text-to-Speech integration using PowerShell"""
    
    def __init__(self):
        self.enabled = True
        self.speaking = False
        self._voice_rate = 1  # -10 to 10 (default 0, faster is positive)
        
    def speak(self, text, async_mode=True):
        """Speak text using Windows Speech API via PowerShell"""
        if not self.enabled or self.speaking:
            return
        
        try:
            self.speaking = True
            # Clean text for speech
            text = str(text).replace('"', "'").replace('`', '')
            
            # PowerShell command to speak
            ps_command = f"""Add-Type -AssemblyName System.Speech; $speak = New-Object System.Speech.Synthesis.SpeechSynthesizer; $speak.Rate = {self._voice_rate}; $speak.Speak(\"{text}\")"""
            
            if async_mode:
                # Non-blocking speech
                subprocess.Popen(['powershell', '-Command', ps_command], 
                               creationflags=subprocess.CREATE_NO_WINDOW)
            else:
                # Blocking speech
                subprocess.run(['powershell', '-Command', ps_command],
                             creationflags=subprocess.CREATE_NO_WINDOW,
                             timeout=30)
                             
        except Exception as e:
            App.Console.PrintWarning(f"[TTS] Speech error: {e}\n")
        finally:
            # Reset speaking flag after delay
            QtCore.QTimer.singleShot(2000, lambda: setattr(self, 'speaking', False))
    
    def speak_command_result(self, success, command_preview=""):
        """Speak command execution result"""
        if success:
            self.speak(f"Command executed successfully")
        else:
            self.speak(f"Command failed")
    
    def speak_startup(self):
        """Speak startup message"""
        self.speak(f"A I Bridge version {Config.VERSION} connected and ready")
    
    def speak_shutdown(self):
        """Speak shutdown message"""
        self.speak("A I Bridge disconnected")
    
    def speak_error(self, error_type=""):
        """Speak error notification"""
        if error_type:
            self.speak(f"Error: {error_type}")
        else:
            self.speak("An error occurred")
    
    def set_rate(self, rate):
        """Set speech rate (-10 to 10)"""
        self._voice_rate = max(-10, min(10, rate))

# Global TTS instance
_tts = None

# ============================================================
# TECHNICAL DATA REVIEW SYSTEM - Self-Learning Foundation
# ============================================================

class TechDataReviewer:
    """Loads and indexes Technical_Data folder resources on startup"""
    
    def __init__(self):
        self.knowledge_base = {}
        self.expressions_guide = []
        self.python_conventions = []
        self.quick_patterns = {}
        self.loaded = False
        
    def load_all_technical_data(self):
        """Load all technical reference files for self-learning"""
        try:
            tech_dir = os.path.join(os.path.dirname(os.path.dirname(__file__)), 'Macro_03', 'Technical_Data')
            
            if not os.path.exists(tech_dir):
                App.Console.PrintWarning(f"[TECH-DATA] Directory not found: {tech_dir}\n")
                return False
            
            App.Console.PrintMessage("\n[TECH-DATA REVIEW] Loading knowledge resources...\n")
            App.Console.PrintMessage("="*70 + "\n")
            
            # Load FreeCAD Knowledge Base (JSON)
            kb_file = os.path.join(tech_dir, 'FreeCAD_Knowledge_Base.json')
            if os.path.exists(kb_file):
                with open(kb_file, 'r', encoding='utf-8') as f:
                    self.knowledge_base = json.load(f)
                    patterns = self.knowledge_base.get('metadata', {}).get('total_patterns', 0)
                    App.Console.PrintMessage(f"✓ Knowledge Base: {patterns} patterns loaded\n")
                    
                    # Extract quick reference patterns
                    if 'quick_reference' in self.knowledge_base:
                        self.quick_patterns = self.knowledge_base['quick_reference']
                        App.Console.PrintMessage(f"✓ Quick Patterns: {len(self.quick_patterns)} categories\n")
            
            # Load Workbench Knowledge Base (JSON)
            wb_kb_file = os.path.join(tech_dir, 'FreeCAD_Workbenches_Knowledge_Base.json')
            if os.path.exists(wb_kb_file):
                with open(wb_kb_file, 'r', encoding='utf-8') as f:
                    self.workbench_kb = json.load(f)
                    total_wb = self.workbench_kb.get('metadata', {}).get('total_workbenches', 0)
                    App.Console.PrintMessage(f"✓ Workbench Database: {total_wb} workbenches loaded\n")
            else:
                self.workbench_kb = None
            
            # Load Python Patterns Index (JSON)
            py_patterns_file = os.path.join(tech_dir, 'Python_Patterns_Index.json')
            if os.path.exists(py_patterns_file):
                with open(py_patterns_file, 'r', encoding='utf-8') as f:
                    self.python_patterns = json.load(f)
                    pattern_count = sum(len(v) if isinstance(v, (dict, list)) else 1 
                                       for k, v in self.python_patterns.items() 
                                       if k != 'metadata')
                    App.Console.PrintMessage(f"✓ Python Patterns: {pattern_count} patterns indexed\n")
            else:
                self.python_patterns = None
            
            # Load Python Knowledge Base (JSON)
            py_kb_file = os.path.join(tech_dir, 'Python_Standard_Library_Knowledge_Base.json')
            if os.path.exists(py_kb_file):
                with open(py_kb_file, 'r', encoding='utf-8') as f:
                    self.python_kb = json.load(f)
                    total_modules = self.python_kb.get('metadata', {}).get('total_modules', 0)
                    total_patterns = self.python_kb.get('metadata', {}).get('total_patterns', 0)
                    App.Console.PrintMessage(f"✓ Python Database: {total_modules} modules, {total_patterns} patterns\n")
            else:
                self.python_kb = None
            
            # Load Expressions Reference
            expr_file = os.path.join(tech_dir, 'Expressions_Reference.txt')
            if os.path.exists(expr_file):
                with open(expr_file, 'r', encoding='utf-8') as f:
                    self.expressions_guide = f.readlines()
                    App.Console.PrintMessage(f"✓ Expressions Guide: {len(self.expressions_guide)} lines\n")
            
            # Load Python Conventions
            py_file = os.path.join(tech_dir, 'Python_Scripting_Conventions.txt')
            if os.path.exists(py_file):
                with open(py_file, 'r', encoding='utf-8') as f:
                    self.python_conventions = f.readlines()
                    App.Console.PrintMessage(f"✓ Python Conventions: {len(self.python_conventions)} lines\n")
            
            # Load Critical AI Instructions (JSON)
            ai_instructions_file = os.path.join(tech_dir, 'CRITICAL_AI_INSTRUCTIONS.json')
            if os.path.exists(ai_instructions_file):
                with open(ai_instructions_file, 'r', encoding='utf-8') as f:
                    self.ai_instructions = json.load(f)
                    App.Console.PrintMessage(f"✓ Critical AI Instructions loaded\n")
            else:
                self.ai_instructions = None
            
            # Load Macro Collection Quick Reference (JSON)
            macro_index_file = os.path.join(tech_dir, 'Macro_Collection_Quick_Reference.json')
            if os.path.exists(macro_index_file):
                with open(macro_index_file, 'r', encoding='utf-8') as f:
                    self.macro_index = json.load(f)
                    total = self.macro_index.get('metadata', {}).get('total_macros', 0)
                    App.Console.PrintMessage(f"✓ Macro Index: {total} macros available\n")
            else:
                self.macro_index = None
            
            # Load AI Bridge Python Rules
            python_rules_file = os.path.join(tech_dir, 'AI_Bridge_Python_Rules.txt')
            if os.path.exists(python_rules_file):
                with open(python_rules_file, 'r', encoding='utf-8') as f:
                    self.python_rules = f.readlines()
                    App.Console.PrintMessage(f"✓ AI Bridge Python Rules: {len(self.python_rules)} lines\n")
            else:
                self.python_rules = None

            # Load other reference files
            ref_files = [
                'Part_Scripting_Reference.txt',
                'Parametric_Objects_Reference.txt',
                'GUI_Creation_Reference.txt',
                'INDEX.txt',
                'README.txt'
            ]
            
            for ref_file in ref_files:
                path = os.path.join(tech_dir, ref_file)
                if os.path.exists(path):
                    App.Console.PrintMessage(f"✓ {ref_file} available\n")
            
            App.Console.PrintMessage("="*70 + "\n")
            App.Console.PrintMessage("[TECH-DATA] All resources loaded successfully\n\n")
            self.loaded = True
            return True
            
        except Exception as e:
            App.Console.PrintError(f"[TECH-DATA] Load error: {e}\n")
            return False
    
    def get_pattern(self, category, operation):
        """Get quick pattern from knowledge base"""
        try:
            if category in self.quick_patterns:
                cat_data = self.quick_patterns[category]
                if operation in cat_data:
                    return cat_data[operation]
        except:
            pass
        return None
    
    def search_for_error(self, error_text):
        """Search ALL technical documentation for error-related content"""
        results = []
        error_lower = error_text.lower()
        
        # Extract key error terms with enhanced extraction
        error_keywords = self._extract_error_keywords(error_text)
        
        # Search Python conventions
        if hasattr(self, 'python_conventions') and self.python_conventions:
            matches = self._search_text_lines(self.python_conventions, error_keywords)
            if matches:
                results.append({
                    'file': 'Python_Scripting_Conventions.txt',
                    'matches': matches[:5],
                    'relevance': 'high' if 'SyntaxError' in error_text or 'NameError' in error_text else 'medium'
                })
        
        # Search expressions guide
        if hasattr(self, 'expressions_guide') and self.expressions_guide:
            matches = self._search_text_lines(self.expressions_guide, error_keywords)
            if matches:
                results.append({
                    'file': 'Expressions_Reference.txt',
                    'matches': matches[:5],
                    'relevance': 'medium'
                })
        
        # NEW: Search FreeCAD Knowledge Base JSON
        if hasattr(self, 'knowledge_base') and self.knowledge_base:
            kb_matches = []
            if 'quick_reference' in self.knowledge_base:
                for category, items in self.knowledge_base['quick_reference'].items():
                    if isinstance(items, dict):
                        for key, value in items.items():
                            value_str = str(value).lower()
                            if any(kw in value_str or kw in category.lower() or kw in key.lower() 
                                   for kw in error_keywords):
                                kb_matches.append({
                                    'category': category,
                                    'operation': key,
                                    'pattern': str(value)[:200]
                                })
            if kb_matches:
                results.append({
                    'file': 'FreeCAD_Knowledge_Base.json',
                    'matches': kb_matches[:5],
                    'relevance': 'high'
                })
        
        # NEW: Search Python Patterns Index
        if hasattr(self, 'python_patterns') and self.python_patterns:
            pattern_matches = []
            for category, items in self.python_patterns.items():
                if category == 'metadata':
                    continue
                if isinstance(items, dict):
                    for key, value in items.items():
                        if any(kw in key.lower() or kw in str(value).lower() 
                               for kw in error_keywords):
                            pattern_matches.append({
                                'category': category,
                                'pattern': key,
                                'example': str(value)[:200] if isinstance(value, str) else str(value)[:200]
                            })
            if pattern_matches:
                results.append({
                    'file': 'Python_Patterns_Index.json',
                    'matches': pattern_matches[:5],
                    'relevance': 'medium'
                })
        
        # NEW: Search Workbench Knowledge Base
        if hasattr(self, 'workbench_kb') and self.workbench_kb:
            wb_matches = []
            for wb_name, wb_info in self.workbench_kb.get('core_workbenches', {}).items():
                if any(kw in wb_name.lower() or kw in wb_info.get('description', '').lower() 
                       for kw in error_keywords):
                    wb_matches.append({
                        'workbench': wb_name,
                        'description': wb_info.get('description', '')[:200]
                    })
            if wb_matches:
                results.append({
                    'file': 'FreeCAD_Workbenches_Knowledge_Base.json',
                    'matches': wb_matches[:3],
                    'relevance': 'low'
                })
        
        return results
    
    def _extract_error_keywords(self, error_text):
        """Extract meaningful keywords from error message"""
        error_lower = error_text.lower()
        
        # Type-specific keywords
        if 'SyntaxError' in error_text:
            return ['syntax', 'quote', 'indentation', 'colon', 'parenthesis', 'bracket', 'string']
        elif 'NameError' in error_text:
            keywords = ['import', 'variable', 'function', 'module', 'undefined']
            # Extract the actual name that's not defined
            import re
            match = re.search(r"name '(\w+)' is not defined", error_text)
            if match:
                keywords.append(match.group(1).lower())
            return keywords
        elif 'AttributeError' in error_text:
            keywords = ['attribute', 'method', 'property', 'object', 'api']
            # Extract object and attribute names
            import re
            match = re.search(r"'(\w+)' object has no attribute '(\w+)'", error_text)
            if match:
                keywords.extend([match.group(1).lower(), match.group(2).lower()])
            return keywords
        elif 'TypeError' in error_text:
            return ['type', 'argument', 'parameter', 'function', 'call']
        elif 'IndexError' in error_text:
            return ['index', 'list', 'array', 'range', 'bounds']
        elif 'KeyError' in error_text:
            return ['key', 'dictionary', 'dict', 'mapping']
        else:
            # Generic extraction
            import re
            words = re.findall(r'\w+', error_lower)
            # Filter out common words
            stop_words = {'the', 'a', 'an', 'is', 'are', 'was', 'were', 'be', 'been', 'being',
                          'have', 'has', 'had', 'do', 'does', 'did', 'will', 'would', 'should',
                          'can', 'could', 'may', 'might', 'must', 'shall'}
            return [w for w in words if len(w) > 3 and w not in stop_words][:10]
    
    def _search_text_lines(self, lines, keywords):
        """Search text lines for keywords"""
        matches = []
        for i, line in enumerate(lines):
            line_lower = line.lower()
            if any(keyword in line_lower for keyword in keywords):
                matches.append({
                    'line_number': i + 1,
                    'content': line.strip()[:200]
                })
        return matches
    
    def search_knowledge(self, query):
        """Search knowledge base for relevant information"""
        results = []
        query_lower = query.lower()
        
        # Search quick patterns
        for category, items in self.quick_patterns.items():
            if query_lower in category.lower():
                results.append({'category': category, 'data': items})
            elif isinstance(items, dict):
                for key, value in items.items():
                    if query_lower in key.lower() or query_lower in str(value).lower():
                        results.append({'category': category, 'key': key, 'data': value})
        
        return results
    
    def search_workbenches(self, query):
        """Search workbench knowledge base"""
        if not self.workbench_kb:
            return []
        
        query_lower = query.lower()
        results = []
        
        # Search core workbenches
        for wb_name, wb_info in self.workbench_kb.get('core_workbenches', {}).items():
            if query_lower in wb_name.lower() or query_lower in wb_info.get('description', '').lower():
                results.append({
                    'name': wb_name,
                    'type': 'core',
                    'description': wb_info.get('description', ''),
                    'key_commands': wb_info.get('key_commands', [])[:3]
                })
        
        # Search external workbenches
        for category, workbenches in self.workbench_kb.get('external_workbenches', {}).items():
            if not isinstance(workbenches, list):
                continue
            for wb in workbenches:
                if query_lower in wb.get('name', '').lower() or query_lower in wb.get('description', '').lower():
                    results.append({
                        'name': wb.get('name', ''),
                        'type': 'external',
                        'category': category.replace('_', ' ').title(),
                        'description': wb.get('description', ''),
                        'status': wb.get('status', 'unknown')
                    })
        
        return results[:10]  # Limit to top 10 results
    
    def search_python_modules(self, query):
        """Search Python stdlib modules"""
        if not self.python_kb:
            return []
        
        query_lower = query.lower()
        results = []
        
        for module_name, module_info in self.python_kb.get('essential_modules', {}).items():
            if query_lower in module_name.lower() or query_lower in module_info.get('description', '').lower():
                results.append({
                    'module': module_name,
                    'description': module_info.get('description', ''),
                    'patterns': list(module_info.get('common_patterns', {}).keys())[:3]
                })
        
        return results[:10]

# Global Tech Data Reviewer
_tech_reviewer = None

# ============================================================
# SELF-HEALING SYSTEM
# ============================================================

class SelfHealingSystem:
    """Automatic error detection and recovery system"""
    
    def __init__(self, learning_system):
        self.learning_system = learning_system
        self.health_checks = []
        self.last_check_time = None
        self.issues_detected = []
        self.auto_fixes_applied = 0
        
    def run_health_check(self):
        """Comprehensive system health check"""
        self.issues_detected = []
        self.last_check_time = datetime.now()
        
        try:
            # Check 1: File system integrity
            if not os.path.exists(AI_INPUT_FILE):
                self.issues_detected.append('INPUT_FILE_MISSING')
                self._fix_missing_input_file()
            
            if not os.path.exists(AI_OUTPUT_FILE):
                self.issues_detected.append('OUTPUT_FILE_MISSING')
                self._fix_missing_output_file()
            
            # Check 2: File permissions
            if not os.access(AI_INPUT_FILE, os.R_OK):
                self.issues_detected.append('INPUT_FILE_NO_READ')
            
            if not os.access(AI_OUTPUT_FILE, os.W_OK):
                self.issues_detected.append('OUTPUT_FILE_NO_WRITE')
                self._fix_output_permissions()
            
            # Check 3: File size limits
            if os.path.exists(AI_OUTPUT_FILE):
                size = os.path.getsize(AI_OUTPUT_FILE)
                if size > Config.MAX_OUTPUT_FILE_SIZE:
                    self.issues_detected.append('OUTPUT_FILE_TOO_LARGE')
                    self._archive_and_rotate_output()
            
            # Check 4: Database integrity
            if self.learning_system:
                if not self.learning_system._validate_schema(self.learning_system.db):
                    self.issues_detected.append('DATABASE_CORRUPTED')
                    self._fix_corrupted_database()
            
            # Check 5: Memory/processed IDs cleanup
            if _state and len(_state._processed_command_ids) > 10000:
                self.issues_detected.append('MEMORY_CLEANUP_NEEDED')
                self._cleanup_old_command_ids()
            
            if self.issues_detected:
                App.Console.PrintWarning(f"[SELF-HEAL] Detected {len(self.issues_detected)} issues\n")
                for issue in self.issues_detected:
                    App.Console.PrintWarning(f"  - {issue}\n")
            
            return len(self.issues_detected) == 0
            
        except Exception as e:
            App.Console.PrintError(f"[SELF-HEAL] Health check error: {e}\n")
            return False
    
    def _fix_missing_input_file(self):
        """Create missing input file"""
        try:
            os.makedirs(os.path.dirname(AI_INPUT_FILE), exist_ok=True)
            with open(AI_INPUT_FILE, 'w', encoding='utf-8') as f:
                f.write('')
            App.Console.PrintMessage("[SELF-HEAL] ✓ Created missing input file\n")
            self.auto_fixes_applied += 1
        except Exception as e:
            App.Console.PrintError(f"[SELF-HEAL] Failed to create input file: {e}\n")
    
    def _fix_missing_output_file(self):
        """Create missing output file"""
        try:
            os.makedirs(os.path.dirname(AI_OUTPUT_FILE), exist_ok=True)
            with open(AI_OUTPUT_FILE, 'w', encoding='utf-8') as f:
                f.write('')
            App.Console.PrintMessage("[SELF-HEAL] ✓ Created missing output file\n")
            self.auto_fixes_applied += 1
        except Exception as e:
            App.Console.PrintError(f"[SELF-HEAL] Failed to create output file: {e}\n")
    
    def _fix_output_permissions(self):
        """Attempt to fix output file permissions"""
        try:
            # Windows: Remove read-only attribute
            import stat
            os.chmod(AI_OUTPUT_FILE, stat.S_IWRITE | stat.S_IREAD)
            App.Console.PrintMessage("[SELF-HEAL] ✓ Fixed output file permissions\n")
            self.auto_fixes_applied += 1
        except Exception as e:
            App.Console.PrintError(f"[SELF-HEAL] Failed to fix permissions: {e}\n")
    
    def _archive_and_rotate_output(self):
        """Archive and rotate large output file"""
        try:
            timestamp = datetime.now().strftime("%Y%m%d_%H%M%S")
            archive_file = f"{AI_OUTPUT_FILE}.archive.{timestamp}"
            os.rename(AI_OUTPUT_FILE, archive_file)
            
            with open(AI_OUTPUT_FILE, 'w', encoding='utf-8') as f:
                f.write('')
            
            App.Console.PrintMessage(f"[SELF-HEAL] ✓ Archived large output file\n")
            self.auto_fixes_applied += 1
        except Exception as e:
            App.Console.PrintError(f"[SELF-HEAL] Failed to rotate output: {e}\n")
    
    def _fix_corrupted_database(self):
        """Restore database from backup"""
        try:
            backup_path = f"{self.learning_system.db_path}.backup"
            if os.path.exists(backup_path):
                with open(backup_path, 'r', encoding='utf-8') as f:
                    backup_data = json.load(f)
                self.learning_system.db = backup_data
                App.Console.PrintMessage("[SELF-HEAL] ✓ Restored database from backup\n")
                self.auto_fixes_applied += 1
        except Exception as e:
            App.Console.PrintError(f"[SELF-HEAL] Failed to restore database: {e}\n")
    
    def _cleanup_old_command_ids(self):
        """Clean up old processed command IDs to prevent memory bloat"""
        try:
            if _state:
                old_count = len(_state._processed_command_ids)
                # Keep only recent 5000 IDs
                _state._processed_command_ids = set(list(_state._processed_command_ids)[-5000:])
                new_count = len(_state._processed_command_ids)
                App.Console.PrintMessage(f"[SELF-HEAL] ✓ Cleaned {old_count - new_count} old command IDs\n")
                self.auto_fixes_applied += 1
        except Exception as e:
            App.Console.PrintError(f"[SELF-HEAL] Failed to cleanup IDs: {e}\n")

# Global self-healing system
_self_healing = None

# ============================================================
# CONFIGURATION CONSTANTS
# ============================================================

class Config:
    """Production-ready configuration with safe defaults"""
    VERSION = "5.0.21"  # SINGLE SOURCE OF TRUTH for the Bridge version
    #                    user-facing string (TTS, GUI title, console banner)
    #                    derives from this. Bump ONLY here.
    #                    3.3.0: Imagineering GUI rebrand. Prev 3.2.0: self-learning
    #                    wired (templates + mistakes -> AI context summary).
    CONFIG_VERSION = "1.1"
    
    # Timing constants (milliseconds)
    POLL_INTERVAL_MS = 500              # Command checking frequency (reduced to prevent event saturation)
    STATUS_UPDATE_INTERVAL_MS = 5000    # Status file update frequency
    BUFFER_FLUSH_INTERVAL_MS = 5000     # Result buffer flush frequency
    HEALTH_CHECK_INTERVAL_MS = 10000    # Health check update frequency
    SELF_HEAL_CHECK_MS = 30000          # Self-healing check interval
    
    # Technical Data paths for self-learning
    TECH_DATA_DIR = os.path.join(os.path.dirname(os.path.dirname(__file__)), 'Macro_03', 'Technical_Data')
    KNOWLEDGE_BASE_FILE = os.path.join(TECH_DATA_DIR, 'FreeCAD_Knowledge_Base.json') if os.path.exists(os.path.join(os.path.dirname(os.path.dirname(__file__)), 'Macro_03', 'Technical_Data')) else None
    WORKBENCH_KB_FILE = os.path.join(TECH_DATA_DIR, 'FreeCAD_Workbenches_Knowledge_Base.json') if os.path.exists(os.path.join(os.path.dirname(os.path.dirname(__file__)), 'Macro_03', 'Technical_Data')) else None
    PYTHON_PATTERNS_FILE = os.path.join(TECH_DATA_DIR, 'Python_Patterns_Index.json') if os.path.exists(os.path.join(os.path.dirname(os.path.dirname(__file__)), 'Macro_03', 'Technical_Data')) else None
    EXPRESSIONS_REF = os.path.join(TECH_DATA_DIR, 'Expressions_Reference.txt') if os.path.exists(os.path.join(os.path.dirname(os.path.dirname(__file__)), 'Macro_03', 'Technical_Data')) else None
    PYTHON_CONVENTIONS = os.path.join(TECH_DATA_DIR, 'Python_Scripting_Conventions.txt') if os.path.exists(os.path.join(os.path.dirname(os.path.dirname(__file__)), 'Macro_03', 'Technical_Data')) else None
    CRITICAL_AI_INSTRUCTIONS = os.path.join(TECH_DATA_DIR, 'CRITICAL_AI_INSTRUCTIONS.json') if os.path.exists(os.path.join(os.path.dirname(os.path.dirname(__file__)), 'Macro_03', 'Technical_Data')) else None
    MACRO_COLLECTION_INDEX = os.path.join(TECH_DATA_DIR, 'Macro_Collection_Quick_Reference.json') if os.path.exists(os.path.join(os.path.dirname(os.path.dirname(__file__)), 'Macro_03', 'Technical_Data')) else None
    
    # Text-to-Speech
    TTS_ENABLED = True                   # Enable voice feedback
    TTS_SPEAK_STARTUP = True             # Speak on startup
    TTS_SPEAK_COMMANDS = True            # Speak command results
    TTS_SPEAK_ERRORS = True              # Speak errors
    
    # Execution limits
    COMMAND_TIMEOUT_SEC = 30            # (advisory) soft budget per command
    MAX_COMMAND_LENGTH = 10000          # Max characters in command
    MAX_CONSECUTIVE_ERRORS = 3          # Before automatic restart
    RESTART_COOLDOWN_MS = 5000          # Delay before restart

    # v3.3.3: GUI-freeze watchdog (detect, warn, never block - Rule 42)
    WATCHDOG_ENABLED = True             # Background daemon that detects GUI-thread freezes
    WATCHDOG_WARN_SEC = COMMAND_TIMEOUT_SEC   # Warn once a command holds the GUI this long
    WATCHDOG_SAMPLE_SEC = 2.0           # Watchdog sampling interval (on its own thread)
    # v3.4.7: how long a GUI-thread timer may go without
    # ticking before the watchdog declares it dead. The command
    # poll runs every POLL_INTERVAL_MS (500ms), so 20s is 40
    # missed ticks - far outside normal jitter, and short enough
    # that an agent notices inside one command timeout.
    WATCHDOG_TIMER_DEAD_SEC = 20
    # v3.4.9: how long one command may hold the execution latch before the
    # watchdog calls it stuck rather than slow. Past this point every
    # command sent is being dropped on the floor, because the poll returns
    # immediately while the latch is set. Three command timeouts.
    WATCHDOG_COMMAND_STUCK_SEC = 90
    
    # ========================================================
    # v3.4.0: OLLAMA - LOCAL AI AGENT [PHASE 1]
    # ========================================================
    OLLAMA_ENABLED = True                # Master switch. False = full v3.3.3 behaviour
    OLLAMA_PROVIDER = "ollama"           # "ollama" (local) | "openrouter" (cloud fallback)
    OLLAMA_HOST = "http://localhost:11434"
    OLLAMA_MODEL = "qwen3-coder:30b"     # 30B MoE / 3.3B active - 30B quality at ~3B speed.
    #                                      Fallback for smaller boxes: qwen2.5-coder:14b
    OLLAMA_NUM_CTX = 16384               # MUST be explicit. Ollama's default is 4096 and it
    #                                      truncates the prompt SILENTLY - your injected rules
    #                                      would simply vanish with nothing in the log.
    OLLAMA_TEMPERATURE = 0.15            # Low: we want template compliance, not creativity
    OLLAMA_TOP_P = 0.9
    OLLAMA_KEEP_ALIVE = "5m"             # Unload after idle instead of squatting on VRAM
    OLLAMA_REQUEST_TIMEOUT_SEC = 180     # Hard socket timeout per generation
    OLLAMA_CONNECT_TIMEOUT_SEC = 5       # Probe timeout for /api/tags
    OLLAMA_AUTOSTART_SERVER = True       # Run `ollama serve` on demand if not reachable
    OLLAMA_SERVER_BOOT_WAIT_SEC = 15     # How long to wait for a cold server to answer

    # Cloud fallback (same client, different backend) - reuses your OpenRouter free tier
    OPENROUTER_HOST = "https://openrouter.ai/api"
    OPENROUTER_MODEL = "qwen/qwen3-coder-480b-a35b:free"
    OPENROUTER_API_KEY = ""              # Leave blank to keep this path disabled

    OLLAMA_AGENT_ID = "ollama"           # agent_id stamped on every command it will eventually send
    OLLAMA_CONTEXT_BUDGET_TOKENS = 6000  # Ceiling for injected knowledge (Phase 4)
    OLLAMA_MAX_REPAIR_ATTEMPTS = 2       # Auto-repair loop cap (Phase 6)
    OLLAMA_AUTO_EXECUTE = False          # Review-before-execute is the default (Phase 5)
    OLLAMA_HEARTBEAT_MS = 100            # GUI liveness spinner - proves the event loop is alive

    # v3.4.0 Phase 8: registration handshake.
    # *** BEHAVIOUR CHANGE ***  With this True, ANY agent (including Claude
    # Code) must send {'type':'hello','agent_id':...} and receive the current
    # context before its execute/run_macro commands are accepted. Rejected
    # commands get a 'registration_required' response containing the context,
    # so a well-behaved agent self-corrects on the next turn. Set False to
    # restore v3.3.3 open-door behaviour.
    REQUIRE_AGENT_REGISTRATION = True

    # File size limits (bytes)
    MAX_INPUT_FILE_SIZE = 10 * 1024 * 1024    # 10 MB
    MAX_OUTPUT_FILE_SIZE = 50 * 1024 * 1024   # 50 MB
    MAX_ARCHIVE_FILES = 10                     # Keep last N archives
    
    # Database limits
    MAX_SUCCESSFUL_PATTERNS = 1000
    MAX_ERROR_RESOLUTIONS = 500
    MAX_COMMON_MISTAKES = 100
    MAX_DATABASE_BACKUPS = 5
    
    # Security
    ALLOWED_MODULES = {
        'App', 'Gui', 'FreeCAD', 'FreeCADGui',
        'Part', 'Draft', 'Sketcher', 'Mesh',
        'math', 'datetime', 'PartDesign', 'Arch',
        'TechDraw', 'Path', 'Spreadsheet'
    }
    
    FORBIDDEN_PATTERNS = [
        'import os', 'import sys', 'import subprocess',
        '__import__', 'exec(', 'eval(', 'compile(',
        'open(', 'file(', 'input(', 'raw_input(',
        'os.system', 'os.popen', 'os.exec',
        '__builtins__', 'globals()', 'locals()',
        'delattr', 'setattr('
    ]

# Clear problematic Python executable path preference on startup
try:
    param = App.ParamGet("User parameter:BaseApp/Preferences/General")
    current_path = param.GetString("PythonExecutable", "")
    if current_path:
        param.SetString("PythonExecutable", "")
        App.Console.PrintMessage(f"[OK] Cleared Python executable path: {current_path}\n")
except Exception as e:
    App.Console.PrintWarning(f"Could not clear Python path: {str(e)}\n")

# ============================================================
# IDE MANAGER - Multi-IDE Detection & Launch
# ============================================================

# ===========================================================================
# WHERE THINGS ARE -- worked out, not hardcoded
# ---------------------------------------------------------------------------
# Until 3.5.2 the run_macro allowlist named one folder on one machine:
#
#     ALLOWED_ROOTS = [r'<one operator's own Desktop folder>', ...]
#
# so on anybody else's computer the Bridge answered "Macro path rejected" to
# everything an agent asked it to run -- the headline feature, dead, with no
# clue as to why. Everything below is derived from FreeCAD itself.
# ===========================================================================
def _macro_own_dir():
    """The folder this macro is running from, or '' if that is unknowable."""
    try:
        return os.path.dirname(os.path.abspath(__file__))
    except BaseException:
        return ""


def _suite_root():
    """The parent of this macro's folder.

    This suite keeps the loader in Macro_Loader/, development in Dev/ and the
    macros themselves in Macro_03/<discipline>/ -- all siblings. So the
    useful root is one level up from wherever this file sits, not the folder
    itself. Measured: App.getUserMacroDir(True) returns
    .../Macro_Directory/Macro_Loader here, which does NOT contain
    .../Macro_Directory/Macro_03, so deriving from that call alone would
    reject the operator's own macros.
    """
    own = _macro_own_dir()
    return os.path.dirname(own) if own else ""


def _find_suite_dir(*parts, **kw):
    """Walk up from this macro looking for a folder, e.g.
    _find_suite_dir('Macro_03', 'Technical_Data'). '' if it is not there.

    Replaces four absolute paths that named one machine's home folder. Each
    degraded quietly on another machine -- the knowledge base simply never
    loaded -- and published this operator's username and folder layout to
    anyone reading the file.
    """
    levels = kw.get("levels", 5)
    here = _macro_own_dir()
    for _ in range(levels):
        if not here:
            break
        candidate = os.path.join(here, *parts)
        if os.path.isdir(candidate):
            return candidate
        parent = os.path.dirname(here)
        if parent == here:
            break
        here = parent
    return ""


def _cfg_get(key, default=""):
    """One value out of ai_config.json. Never raises; '' when absent."""
    try:
        if os.path.exists(AI_CONFIG_FILE):
            with open(AI_CONFIG_FILE, "r", encoding="utf-8") as fh:
                return (json.load(fh) or {}).get(key, default) or default
    except BaseException:
        pass
    return default


def _cfg_set(key, value):
    """Store one value in ai_config.json, leaving the rest alone. An empty
    value removes the key, i.e. back to the worked-out default."""
    try:
        cfg = {}
        if os.path.exists(AI_CONFIG_FILE):
            with open(AI_CONFIG_FILE, "r", encoding="utf-8") as fh:
                cfg = json.load(fh) or {}
        if value:
            cfg[key] = value
        else:
            cfg.pop(key, None)
        os.makedirs(os.path.dirname(AI_CONFIG_FILE), exist_ok=True)
        with open(AI_CONFIG_FILE, "w", encoding="utf-8") as fh:
            json.dump(cfg, fh, indent=2)
        return True, "Saved to %s" % AI_CONFIG_FILE
    except BaseException as exc:
        return False, "Could not write %s: %s" % (AI_CONFIG_FILE, exc)


def _cfg_list(key):
    """A config value as a list of paths. Accepts a bare string too, so a
    setting written by an earlier version still reads."""
    v = _cfg_get(key, "")
    if isinstance(v, str):
        return [v.strip()] if v.strip() else []
    try:
        return [str(x).strip() for x in v if str(x).strip()]
    except BaseException:
        return []


def learning_sources():
    """Every learning database worth reading: the one being written,
    then any extra sources the operator added. Deduplicated, existing
    files only."""
    out, seen = [], set()
    cand = [LEARNING_DIR] + _cfg_list("learning_dir")[1:]
    for d in cand:
        if not d:
            continue
        p = os.path.join(d, "AI_Learning_Database.json")
        k = os.path.normcase(os.path.normpath(p))
        if k in seen or not os.path.isfile(p):
            continue
        seen.add(k)
        out.append(p)
    return out


def library_dirs():
    """Every folder to search for reference material, in order.

    v4.0.11: a list, because there is no reason a technical database has
    to be one folder -- a shared library and a project's own notes are
    both legitimate, and asking the operator to choose is asking the wrong
    question.
    """
    out = [os.path.normpath(p) for p in _cfg_list("library_dir")]
    if not out:
        found = _tech_data_dir()
        out = [found] if found else [
            os.path.join(App.getUserAppDataDir(), "AI_Library")]
    return out


def library_file(name, *parts):
    """The first copy of a reference file across the library folders, or
    '' if no folder has it. Callers that want a path to WRITE should not
    use this; nothing writes to the library."""
    for d in library_dirs():
        p = os.path.join(d, *(list(parts) + [name])) if parts \
            else os.path.join(d, name)
        if os.path.exists(p):
            return p
    return ""


def library_dir():
    """The technical database the Bridge READS and never writes to:
    knowledge bases, scripting references, the Python rules, pattern
    indexes.

    v4.0.05: this was CALLED by 4.0.03 and never defined -- the patch meant
    to add it failed on an anchor and the call shipped anyway. A bare except
    swallowed the NameError, so the technique count just went blank.

    Order: ai_config.json 'library_dir', set in the Locations tab; then
    Macro_03/Technical_Data found by walking up from this macro; then a
    folder under FreeCAD's user data. The path need not exist -- every
    reader copes with a missing file, and the Locations tab reports what it
    can actually see.
    """
    # The FIRST library folder. Kept for callers that want somewhere to
    # look rather than a particular file; library_file() is better when a
    # named file is wanted, because it searches all of them.
    return library_dirs()[0]


def _tech_data_dir():
    """<suite>/Macro_03/Technical_Data, found by walking up. May be ''."""
    return _find_suite_dir("Macro_03", "Technical_Data")


def _default_allowed_roots():
    """Folders a macro may be run from. Derived; contains no username.

    In order:
      1. the operator's CONFIGURED macro path -- App.getUserMacroDir(True).
         This is FreeCAD's own answer to "where does this person keep their
         macros", it is what the Macro dialog uses, and FreeCAD resolves it
         per platform rather than us guessing at %APPDATA%.
      2. FreeCAD's default macro path -- getUserMacroDir(False) -- for when
         the configured one is unset or has been changed.
      3. this macro's own folder, and its parent, so a suite laid out in
         sibling folders keeps working wherever it is unpacked.
      4. the FreeCAD user app data directory, which holds AI_Agent_IO.
    """
    roots = []
    for call in (lambda: App.getUserMacroDir(True),
                 lambda: App.getUserMacroDir(False),
                 lambda: App.getUserAppDataDir()):
        try:
            got = call()
            if got:
                roots.append(got)
        except BaseException:
            pass
    for extra in (_macro_own_dir(), _suite_root()):
        if extra:
            roots.append(extra)
    # Anything the operator added in ai_config.json. Additive on purpose --
    # it is how someone keeps macros somewhere unusual without editing this
    # file. A root short enough to be a drive or filesystem root is refused:
    # 'C:\\' or '/' would allow the whole machine.
    try:
        if os.path.exists(AI_CONFIG_FILE):
            with open(AI_CONFIG_FILE, "r", encoding="utf-8") as fh:
                cfg = json.load(fh) or {}
            for extra in (cfg.get("allowed_roots") or []):
                extra = str(extra or "").strip()
                if not extra:
                    continue
                norm = os.path.normpath(extra)
                if len(norm.rstrip(os.sep).split(os.sep)) < 3:
                    App.Console.PrintWarning(
                        "[SECURITY] allowed_roots entry %r is too close to "
                        "the filesystem root to be safe; ignored.\n" % extra)
                    continue
                roots.append(norm)
    except BaseException as exc:
        App.Console.PrintWarning(
            "[SECURITY] Could not read allowed_roots from %s: %s\n"
            % (AI_CONFIG_FILE, exc))

    out, seen = [], set()
    for r in roots:
        norm = os.path.normcase(os.path.normpath(r))
        if norm and norm not in seen:
            seen.add(norm)
            out.append(os.path.normpath(r))
    return out


def _within_root(path, root):
    """Is path inside root? Compared on a path BOUNDARY, not as a string.

    3.5.1 used norm_lower.startswith(root.lower()), so a sibling folder
    called Macro_Directory_Evil satisfied a root of Macro_Directory. The
    separator is what makes it a containment test rather than a prefix test.
    """
    try:
        p = os.path.normcase(os.path.normpath(path))
        r = os.path.normcase(os.path.normpath(root)).rstrip(os.sep)
        return p == r or p.startswith(r + os.sep)
    except BaseException:
        return False


def validate_macro_path(macro_path, roots=None):
    """(ok, reason, normalised_path) for a run_macro request.

    normpath collapses '..', so traversal out of a root fails the containment
    test below. Acknowledged limit: a symlink or junction planted INSIDE an
    allowed root can still point outside it, and the path is deliberately not
    resolved through links -- this installation reaches its own Mod folders
    through junctions, and resolving them would reject macros that are
    perfectly legitimate. Planting such a link requires write access to the
    operator's own macro folder.
    """
    roots = roots if roots is not None else _default_allowed_roots()
    try:
        norm = os.path.normpath(str(macro_path or ""))
    except BaseException:
        return False, "that is not a usable path", ""
    if not norm or norm == ".":
        return False, "no macro path was given", ""
    if not norm.lower().endswith((".fcmacro", ".py")):
        return False, "only .FCMacro and .py files can be run", norm
    if not os.path.isfile(norm):
        return False, "there is no file at %s" % norm, norm
    if not any(_within_root(norm, r) for r in roots):
        return False, ("%s is outside every folder this Bridge may run "
                       "macros from. Those are:\n%s\nAdd another under "
                       "\"allowed_roots\" in %s if you keep macros "
                       "elsewhere."
                       % (norm, "\n".join("  - " + r for r in roots),
                          AI_CONFIG_FILE)), norm
    return True, "", norm


# ===========================================================================
# VISUAL CAPTURE -- runs in a SECOND FreeCAD process
# ---------------------------------------------------------------------------
# Rendering in the GUI process freezes FreeCAD for as long as it takes. On a
# 161-object assembly that is about four seconds, every time. FreeCADCmd is
# a separate process on a separate core, so the operator's session carries
# on untouched -- which is also how this macro's own test suite runs while
# the Bridge is live.
#
# Headless FreeCAD CAN render: SoOffscreenRenderer works, but writeToFile()
# does not (getNumWriteFiletypes() returns 0, no image plugin is
# registered). getBuffer() hands back raw RGB and PIL writes the PNG.
# ===========================================================================
CAPTURE_PRESETS = {
    # name:        slices, grid divisions, width, height, mesh deviation
    "Coarse":      (6,  5,   800,  600, 2.0),
    "Medium":      (12, 10, 1024,  768, 1.0),
    "Fine":        (24, 20, 1600, 1200, 0.5),
    "Ultrafine":   (48, 50, 2048, 1536, 0.2),
}

# The decades an engineer actually works in. One pick sets the mesh
# deviation AND the grid pitch -- see the worker, which clamps either by
# whole decades when the chosen one cannot suit this model, and says so.
CAPTURE_FIDELITY = [
    (0.0, "Auto  -  from the model's own size"),
    (0.001, "0.001 mm"), (0.01, "0.01 mm"), (0.1, "0.1 mm"),
    (1.0, "1 mm"), (10.0, "10 mm"), (100.0, "100 mm"),
    (1000.0, "1 m"), (10000.0, "10 m"), (100000.0, "100 m"),
    (1000000.0, "1 km"),
]

# ============================================================
# OUTSOURCE -- driving other programs, one registry
# ============================================================
# The Bridge's job is widening from "let an agent drive FreeCAD" to "let an
# agent drive the right program for the job and bring the result back".
#
# ---- WHAT MAY GO IN HERE. Read this before adding a target. ----------
#
# THE RULE, from the operator, 2026-11-09, in two steps:
#     "Lets keep this about 3d geometry too much is asking for trouble"
#     "we should also change the Outsourced label on this TAB to Mesh"
#
# THE TEST: does this target work on MESHES? Not "does it touch 3D
# geometry" -- that was the first draft of the rule and it is broad
# enough to argue CAM and FEM into, since both take 3D geometry in.
# Mesh has no such give.
#
# Why meshes specifically: a mesh is what FreeCAD is worst at and what a
# scan arrives as. The whole point is reaching INTERNAL geometry -- wall
# thickness, sections, the inside of a part no outside view shows -- and
# turning a mesh into a solid FreeCAD can actually work with.
#
# This is a deliberate narrowing, decided AFTER the shape was working, so
# it is not caution about the design -- it is a judgement that a Bridge
# claiming to drive everything will do none of it reliably. Every target
# is a surface that can break, and a tab full of half-working targets is
# worse than a short list that works.
#
#   BUILT      ScanRuler -- scan mesh to solid STEP, plus wall
#              thickness and section: the internal geometry a
#              measurement cannot describe.
#
#   CANDIDATES, named by the operator, NOT built and not investigated:
#              MeshLab      mesh repair, decimation, reconstruction
#              Meshroom     photogrammetry; it has an MCP server
#              Blender      mesh editing, remesh, boolean cleanup
#              Each passes the mesh test. None has been checked for
#              licence, Windows build, or whether it can be driven
#              without a human at the keyboard -- and a half-known entry
#              in this list is how the tab fills with things that do not
#              work. Investigate before adding, the way ScanRuler was.
#
#   OUT        GIMP, LibreOffice, ComfyUI, KiCad -- raster images,
#              documents, image generation, schematics. All four have
#              working bridges in HQ/41_AI_Bridge/20_Bridges and that is
#              precisely the temptation this paragraph exists to refuse.
#              An existing bridge is not a reason; passing the test is.
#              Also out, and these are the near misses: CAM, FEM and
#              Render all take 3D geometry, and none of them works on a
#              mesh. They are not mesh tools and do not belong on this
#              tab. Cura and Linkage likewise.
#
# ---- WHY ONE PAGE AND NOT ONE TAB EACH ------------------------------
# One declarative record per target, rendered by ONE page. Seven
# hand-written tabs with four location boxes each would be twenty-eight
# controls and the Start-beside-Connect mistake at scale; and the tab bar
# has a 110 px minimum per tab, so a dozen top-level tabs simply scroll
# off. A target is a dict. Adding the next one is a dict, not a tab --
# which is also what keeps the rule above cheap to obey, because leaving
# a target out costs nothing and adding one is never urgent.
#
# THREE KINDS, and they are genuinely different:
#   web_app            its own app or service; we drive it, never embed it
#   external_bridge    a program with a JSONL bridge already in the estate
#                      (HQ/41_AI_Bridge/99_Deploy/bridge_registry.json
#                      holds eight, program_id 1-8, each with its own
#                      <Name>_IO folder and a written wire contract --
#                      none of which is reinvented here)
#   freecad_workbench  in-process WB that outsources to its own solver
#                      (FEM -> ccx.exe, Render -> LuxCore)
#
# Every kind does its real work in ANOTHER process. That is the multicore
# goal satisfied by construction rather than by assertion.

OUTSOURCE_TARGETS = [
    {
        "key": "scanruler",
        "name": "ScanRuler",
        "kind": "web_app",
        "program_id": 9,
        # Named separately so the page can credit him in its first
        # line rather than in a paragraph someone has to go looking for.
        "author": "Stefan Hermann  -  CNC Kitchen",
        "credit": ("CNC Kitchen -- Stefan Hermann. "
                   "https://github.com/CNCKitchen/ScanRuler"),
        # The long "what" still exists for the drawer; this is the line
        # that belongs at the top of a page someone is trying to use.
        "short": ("Turn a scan mesh into a solid STEP body, and measure "
                  "wall thickness and sections -- the internal geometry "
                  "no outside view of a part will show you."),
        "licence": "AGPL-3.0",
        "licence_note": (
            "Driven as a SEPARATE program -- its website, or its own MCP "
            "server. None of its code is copied into this macro. Embedding "
            "AGPL code here would make this macro AGPL as well, so the rule "
            "for this target is drive it, never vendor it."),
        "what": (
            "Check a 3D scan against the CAD it should have been: fit "
            "spheres, cylinders and planes, paint deviation, map wall "
            "thickness -- and model a scan into a solid STEP body. That "
            "last one is the mesh-to-solid route FreeCAD does not have, "
            "and wall thickness and section are how an agent gets at "
            "INTERNAL geometry, which no outside view shows it."),
        # Passes the registry's admission test outright: 3D geometry in,
        # 3D geometry back.
        "geometry": "in and out",
        "web": "https://scanruler.com/",
        "repo": "https://github.com/CNCKitchen/ScanRuler",
        "privacy": (
            "Its own README: everything is processed in your browser and "
            "never leaves your computer -- UNLESS you connect an AI agent. "
            "Connecting an agent is the step that sends the scan out."),
        "offline": (
            "THE WEBSITE NEEDS THE INTERNET. Checked in the repo: there "
            "is no service worker and no PWA manifest, so it will not "
            "load offline, not even after a first visit. Build it here "
            "and the local route serves from your own machine and works "
            "with no connection at all."),
        # No path to anyone's Desktop is written down here. The folder is
        # discovered under the user's own home, or set on the Locations
        # rows. A hardcoded operator path is the single biggest thing
        # keeping this macro unpublishable.
        "discover": {"leaf": "ScanRuler-main", "marker": "package.json"},
        # How to run it locally, once it has been built. node, not npm:
        # npm is npm.cmd on Windows and a .cmd cannot be started without
        # shell=True. vite has a plain .js entry, so this is node.exe plus
        # a path, with no shell involved.
        "launch": {
            "script": "node_modules/vite/bin/vite.js",
            "url": "http://localhost:{port}/",
            # Tried in order; the first whose directory exists wins.
            # preview serves the BUILT app and is what someone opening a
            # tool wants; dev recompiles on the fly and is for someone
            # editing ScanRuler itself.
            "modes": [
                {"needs": "dist", "port": 4173,
                 "args": ["preview", "--port", "{port}", "--strictPort"],
                 "why": "the built app, served from this machine"},
                {"needs": "node_modules", "port": 5173,
                 "args": ["--port", "{port}", "--strictPort"],
                 "why": "dev server -- nothing built yet, but runnable"},
            ],
        },
        "mcp_rel": "mcp/bin/scanruler-mcp.js",
        "training_rel": "skills/scan-measuring/SKILL.md",
        "build": ["npm ci", "npm --prefix mcp ci"],
        "needs": "Node 22 or newer",
        "push_what": "STL meshes out of FreeCAD, for ScanRuler to measure",
        "pull_what": "STEP solids and meshes back in from ScanRuler",
        "push_fmt": "stl",
        "pull_fmt": ("step", "stp", "stl", "obj", "ply"),
    },
]


def outsource_target(key):
    for t in OUTSOURCE_TARGETS:
        if t.get("key") == key:
            return t
    return None


def _outsource_roots():
    """Where to look for a target's own folder. The user's home, not
    anybody's name: expanduser keeps this working on another machine,
    which is the whole point."""
    home = os.path.expanduser("~")
    out = []
    for p in (os.path.join(home, "Desktop"), home,
              os.path.join(home, "Downloads"), os.path.join(home, "src")):
        if p not in out and os.path.isdir(p):
            out.append(p)
    return out


def outsource_root(t):
    """This target's own folder: configured if set, else discovered, else
    '' meaning not on this machine.

    A GitHub zip unpacks as <leaf>/<leaf>, so both depths are tried and
    the one actually holding the marker file wins -- guessing wrong here
    produces a tab that looks configured and does nothing.
    """
    key = t.get("key", "")
    chosen = str(_cfg_get("outsource.%s.root" % key, "") or "").strip()
    if chosen:
        return os.path.normpath(chosen) if os.path.isdir(chosen) else ""
    disc = t.get("discover") or {}
    leaf, marker = disc.get("leaf", ""), disc.get("marker", "")
    if not leaf:
        return ""
    for r in _outsource_roots():
        for cand in (os.path.join(r, leaf), os.path.join(r, leaf, leaf)):
            if os.path.isdir(cand) and (
                    not marker or os.path.exists(os.path.join(cand, marker))):
                return os.path.normpath(cand)
    return ""


def outsource_paths(t):
    """The four locations, each independently settable.

    The operator asked for exactly this: "a location directory for each of
    the push or pull data independently as well as .md agent training &
    agent database also independently." Defaults sit under the Bridge's
    own I/O directory so a fresh machine needs no setup; training defaults
    to the target's OWN shipped document when it has one, because the
    people who wrote the tool wrote better instructions for it than I
    would.
    """
    key = t.get("key", "")
    base = os.path.join(AI_IO_DIR, "outsource", key)
    root = outsource_root(t)
    rel = t.get("training_rel", "")
    shipped = os.path.join(root, *rel.split("/")) if (root and rel) else ""
    out = {
        "root": root,
        "push": (_cfg_get("outsource.%s.push" % key, "")
                 or os.path.join(base, "push")),
        "pull": (_cfg_get("outsource.%s.pull" % key, "")
                 or os.path.join(base, "pull")),
        "training": (_cfg_get("outsource.%s.training" % key, "")
                     or shipped or os.path.join(base, "training.md")),
        "db": (_cfg_get("outsource.%s.db" % key, "")
               or os.path.join(base, "agent_db.json")),
    }
    return dict((k, os.path.normpath(v) if v else "") for k, v in out.items())


def outsource_state(t):
    """What an operator and an agent both need to know about one target.
    Never raises: a status readout that can break the panel is worse than
    no readout."""
    st = {"name": t.get("name", "?"), "kind": t.get("kind", "?"),
          "root": "", "installed": False, "built": False, "mcp": "",
          "training": "", "training_found": False, "ready": "", "why": ""}
    try:
        p = outsource_paths(t)
        st["root"] = p["root"]
        st["installed"] = bool(p["root"])
        rel = t.get("mcp_rel", "")
        if p["root"] and rel:
            st["mcp"] = os.path.normpath(
                os.path.join(p["root"], *rel.split("/")))
            st["built"] = os.path.isdir(
                os.path.join(p["root"], "node_modules"))
            # "installed" and "built" are not the same thing, and the
            # difference decides which local route runs.
            st["dist"] = os.path.isdir(os.path.join(p["root"], "dist"))
        st["training"] = p["training"]
        st["training_found"] = bool(p["training"]) and os.path.isfile(
            p["training"])
        if t.get("web"):
            st["ready"] = "website"
            st["why"] = "the website needs no install at all"
        if st["installed"] and st["built"]:
            st["ready"] = "local"
            st["why"] = ("built here -- the app itself is served from "
                         "this machine" if st.get("dist")
                         else "installed here, not built yet -- the dev "
                              "server would run")
        elif st["installed"]:
            st["why"] = ("found at %s but not built yet -- %s"
                         % (p["root"], ", ".join(t.get("build") or [])))
        elif not t.get("web"):
            st["ready"] = "missing"
            st["why"] = "not found on this machine"
    except BaseException as exc:
        st["why"] = "could not read this target: %s" % exc
    return st


def _outsource_seen(t, add=None):
    """What has already been pulled in, so "new results" means new. Kept
    in the target's own agent database, which is why that has its own
    location."""
    p = outsource_paths(t)
    db = {}
    try:
        if os.path.isfile(p["db"]):
            with open(p["db"], "r", encoding="utf-8") as fh:
                db = json.load(fh) or {}
    except BaseException:
        db = {}
    seen = list(db.get("pulled") or [])
    if add:
        for a in add:
            if a not in seen:
                seen.append(a)
        db["pulled"] = seen
        db.setdefault("target", t.get("key"))
        db["updated"] = time.strftime("%Y-%m-%d %H:%M:%S")
        try:
            os.makedirs(os.path.dirname(p["db"]), exist_ok=True)
            with open(p["db"], "w", encoding="utf-8") as fh:
                json.dump(db, fh, indent=2)
        except BaseException:
            pass
    return seen


_OUTSOURCE_SERVERS = {}


def _node_exe():
    """node, if this machine has it. Looked up, never assumed: a target
    that needs Node and cannot find it must say so rather than fail at
    the moment the operator presses the button."""
    import shutil
    return shutil.which("node") or ""


def _port_answers(url, timeout=0.4):
    """Is anything listening where this url points?

    A socket connect, not an HTTP request: it must not block the GUI
    thread and it does not matter what the answer says, only that
    something is there.
    """
    try:
        import socket
        try:
            from urllib.parse import urlparse
        except BaseException:
            from urlparse import urlparse
        u = urlparse(url)
        host = u.hostname or "localhost"
        port = u.port or (443 if u.scheme == "https" else 80)
        s = socket.create_connection((host, port), timeout)
        s.close()
        return True
    except BaseException:
        return False


def outsource_launch(t):
    """Open the target. Returns (ok, message, url).

    One button, two routes, and the state decides which -- the operator
    should not have to know whether they have run npm ci to know which
    thing to click. Never raises.
    """
    try:
        p = outsource_paths(t)
        root, lau = p.get("root", ""), (t.get("launch") or {})
        web = t.get("web", "")

        # already serving? just show it again rather than starting a
        # second one on a port the first one holds.
        live = _OUTSOURCE_SERVERS.get(t.get("key"))
        if live is not None and live[0].poll() is None:
            return True, ("Already running locally on %s (pid %d)."
                          % (live[1], live[0].pid)), live[1]

        mode = None
        if root and lau:
            for m in (lau.get("modes") or []):
                if os.path.isdir(os.path.join(root, m.get("needs", ""))):
                    mode = m
                    break
        if mode is None:
            if not web:
                return (False,
                        "Nothing to open: it is not built locally and this "
                        "target has no website.", "")
            why = ("it is not built locally yet" if root
                   else "it is not on this machine")
            return True, ("Opened the website -- %s." % why), web

        node = _node_exe()
        if not node:
            return (True,
                    "It is built here, but Node is not on PATH, so the "
                    "website is the only route. Opened that instead.",
                    web) if web else (
                False, "It is built here but Node is not on PATH.", "")

        script = os.path.join(root, *lau["script"].split("/"))
        if not os.path.isfile(script):
            return (True,
                    "Built, but %s is missing -- opened the website "
                    "instead." % lau["script"], web) if web else (
                False, "Built, but %s is missing." % lau["script"], "")

        port = int(mode.get("port", 5173))
        args = [a.replace("{port}", str(port))
                for a in (mode.get("args") or [])]
        url = lau.get("url", "http://localhost:{port}/").replace(
            "{port}", str(port))

        # Adopt an orphan. Closing FreeCAD does not stop a server this
        # launcher started, so meeting one on the next run is the normal
        # case. Spawning into a held port under --strictPort produces a
        # process that exits at once while we report its pid.
        if _port_answers(url):
            return (True,
                    "Already being served on %s by a server from an "
                    "earlier session -- opened that rather than starting "
                    "a second one. Stop that process if you want a fresh "
                    "build picked up." % url, url)
        import subprocess
        kw = {"cwd": root, "stdout": subprocess.DEVNULL,
              "stderr": subprocess.DEVNULL, "stdin": subprocess.DEVNULL}
        if os.name == "nt":
            # no console window for a background server
            kw["creationflags"] = getattr(subprocess, "CREATE_NO_WINDOW", 0)
        # cwd matters: vite resolves "dist" against the working
        # directory, not against its own script path, so started from
        # anywhere else preview dies with "The directory dist does not
        # exist" while the build sits right there.
        proc = subprocess.Popen([node, script] + args, **kw)

        # Popen returning is not the server starting. Give it a moment
        # and check it is still alive AND answering -- otherwise the
        # operator gets a pid that no longer exists and a browser tab
        # pointed at nothing.
        import time as _t
        deadline = _t.time() + 8.0
        while _t.time() < deadline:
            if proc.poll() is not None:
                return (False,
                        "It started and stopped again straight away "
                        "(exit %s). The usual cause is something else "
                        "already on port %d; %s would say so."
                        % (proc.returncode, port, os.path.basename(script)),
                        "")
            if _port_answers(url):
                break
            _t.sleep(0.3)
        else:
            return (False,
                    "It is running (pid %d) but nothing is answering on "
                    "%s after 8 seconds. Left running so you can look."
                    % (proc.pid, url), "")

        _OUTSOURCE_SERVERS[t.get("key")] = (proc, url)
        return (True,
                "Started locally (pid %d): %s. Opened %s -- no internet "
                "needed. It keeps running until you stop that process or "
                "close FreeCAD." % (proc.pid, mode.get("why", ""), url),
                url)
    except BaseException as exc:
        return False, "Could not open it: %s" % exc, ""


def outsource_push(t, doc, objects=None):
    """Export the chosen solids into this target's push folder.

    Returns (ok, message, path). Never raises. Exporting is quick and the
    operator pressed a button, so this runs here; everything the target
    then DOES with the file happens in its own process.
    """
    try:
        if doc is None:
            return False, "No document open.", ""
        p = outsource_paths(t)
        os.makedirs(p["push"], exist_ok=True)
        names = list(objects or [])
        objs = []
        for o in doc.Objects:
            if names and o.Name not in names:
                continue
            sh = getattr(o, "Shape", None)
            if sh is not None and not sh.isNull() and len(sh.Solids) > 0:
                objs.append(o)
        if not objs:
            return (False,
                    "Nothing to push: no solids %s."
                    % ("among the chosen objects" if names
                       else "in this document"), "")
        stem = os.path.splitext(os.path.basename(
            getattr(doc, "FileName", "") or doc.Name))[0] or "model"
        fmt = t.get("push_fmt", "stl")
        path = os.path.join(p["push"], "%s_%s.%s"
                            % (stem, time.strftime("%Y%m%d_%H%M%S"), fmt))
        import Mesh
        Mesh.export(objs, path)
        if not os.path.isfile(path):
            return False, "The exporter reported no error but wrote " \
                          "nothing to %s" % path, ""
        return (True,
                "Pushed %d solid%s to %s (%.1f MB)."
                % (len(objs), "" if len(objs) == 1 else "s",
                   os.path.basename(path),
                   os.path.getsize(path) / 1048576.0), path)
    except BaseException as exc:
        return False, "The push failed: %s" % exc, ""


def outsource_pull(t, doc):
    """Bring every NEW file in this target's pull folder into the document.

    "New" is tracked in the target's own agent database, so pressing Pull
    twice does not import everything twice -- which is how a round trip
    quietly turns into four copies of the same body.
    """
    try:
        if doc is None:
            return False, "No document open.", []
        p = outsource_paths(t)
        if not os.path.isdir(p["pull"]):
            os.makedirs(p["pull"], exist_ok=True)
            return (False,
                    "Nothing there yet. The folder is %s -- point the "
                    "target's output at it, or set another on the "
                    "Locations rows." % p["pull"], [])
        exts = tuple("." + e.lower().lstrip(".")
                     for e in (t.get("pull_fmt") or ("step", "stp")))
        seen = _outsource_seen(t)
        fresh = []
        for nm in sorted(os.listdir(p["pull"])):
            full = os.path.join(p["pull"], nm)
            if not os.path.isfile(full) or not nm.lower().endswith(exts):
                continue
            stamp = "%s@%d" % (nm, int(os.path.getmtime(full)))
            if stamp in seen:
                continue
            fresh.append((nm, full, stamp))
        if not fresh:
            return (True,
                    "Nothing new in %s. %d file%s already pulled."
                    % (p["pull"], len(seen), "" if len(seen) == 1 else "s"),
                    [])
        got, failed = [], []
        for nm, full, stamp in fresh:
            try:
                if nm.lower().endswith((".step", ".stp")):
                    import Import
                    Import.insert(full, doc.Name)
                else:
                    import Mesh
                    Mesh.insert(full, doc.Name)
                got.append((nm, stamp))
            except BaseException as exc:
                failed.append("%s (%s)" % (nm, exc))
        if got:
            _outsource_seen(t, add=[s for _, s in got])
            doc.recompute()
        msg = "Pulled %d file%s: %s." % (
            len(got), "" if len(got) == 1 else "s",
            ", ".join(n for n, _ in got)) if got else "Nothing imported."
        if failed:
            msg += "  Failed: %s" % "; ".join(failed)
        return bool(got), msg, [n for n, _ in got]
    except BaseException as exc:
        return False, "The pull failed: %s" % exc, []


CAPTURE_WORKER_SRC = """# -*- coding: utf-8 -*-
\"\"\"Visual Capture worker. Runs in a SECOND FreeCAD process.

Reads a job file, writes images and a manifest. Nothing here touches the
operator's live session -- that is the whole point: a 161-object assembly
takes about five seconds to open and mesh, and doing it in the GUI process
would freeze FreeCAD for five seconds every time.

Invoked as:  FreeCADCmd.exe capture_worker.py            (job path in env)
Job and manifest are JSON so the launcher never has to parse output.

Measured on FC1.0_CompactMaster (161 objects, 13 top-level solids):
  open 1.7 s, tessellate 0.3-0.5 s, section 56 ms per plane, render ~0.4 s.
\"\"\"
import io
import json
import math
import os
import time
import traceback

import FreeCAD as App

T0 = time.time()
JOB = os.environ.get("CAPTURE_JOB", "")
job = json.load(io.open(JOB, encoding="utf-8"))
OUT_DIR = job["out_dir"]
LOG = []


def say(s):
    LOG.append("%6.2fs  %s" % (time.time() - T0, s))


def finish(status, **extra):
    man = {"status": status, "job": job, "log": LOG,
           "seconds": round(time.time() - T0, 2)}
    man.update(extra)
    try:
        os.makedirs(OUT_DIR, exist_ok=True)
        with io.open(os.path.join(OUT_DIR, "capture_manifest.json"), "w",
                     encoding="utf-8") as fh:
            json.dump(man, fh, indent=2)
    except BaseException:
        pass
    raise SystemExit(0 if status == "ok" else 1)


try:
    from pivy import coin
    from PIL import Image
    import Part

    os.makedirs(OUT_DIR, exist_ok=True)
    doc = App.openDocument(job["doc"])
    say("opened %s, %d objects" % (os.path.basename(job["doc"]),
                                   len(doc.Objects)))

    # --- the parts worth drawing ------------------------------------
    # Same rule as the document inventory: containers are structure, and a
    # shape consumed by a non-container is counted through its result. The
    # first capture meshed containers AND their children and so tessellated
    # the same geometry about four times over -- 324k facets where there
    # were 85k.
    CONTAINERS = ("App::Part", "App::DocumentObjectGroup", "App::LinkGroup",
                  "Part::Compound")

    def has_solids(o):
        try:
            sh = getattr(o, "Shape", None)
            return sh is not None and not sh.isNull() and len(sh.Solids) > 0
        except BaseException:
            return False

    wanted = set(job.get("objects") or [])
    solids = []
    for o in doc.Objects:
        if getattr(o, "TypeId", "") in CONTAINERS or not has_solids(o):
            continue
        if wanted:
            # An explicit pick from the tree overrides the top-level rule:
            # if the operator asks for a part that happens to sit inside a
            # boolean, they want that part, not its result.
            if o.Name not in wanted and getattr(o, "Label", "") not in wanted:
                continue
        elif any(getattr(p, "TypeId", "") not in CONTAINERS and has_solids(p)
                 for p in (o.InList or [])):
            continue
        solids.append(o)
    if not solids:
        finish("empty", reason="no top-level solids in this document")
    say("%d solids to draw%s" % (len(solids),
                                 " (picked from the tree)"
                                 if wanted else ""))

    def chain(o):
        \"\"\"Every container placement above o, composed.

        o.Shape is in the object's OWN frame: an App::Part above it
        contributes nothing. Measured on 26.3 -- a 20 mm box at local
        (5,10,15) inside a container at (100,0,0) turned 90 degrees reads
        x 5..25 from o.Shape.BoundBox and belongs at x 70..90.
        Part.getShape(transform=True) returns the same wrong answer, so
        the chain is walked by hand, the way the document inventory does.
        \"\"\"
        pl = App.Placement()
        seen, cur = set(), o
        while True:
            up = [p for p in (cur.InList or [])
                  if getattr(p, "TypeId", "") in CONTAINERS
                  and cur in (getattr(p, "Group", []) or [])]
            if not up or up[0].Name in seen:
                break
            seen.add(up[0].Name)
            pl = up[0].Placement.multiply(pl)
            cur = up[0]
        return pl

    # One placed copy per solid, in GLOBAL coordinates. Everything
    # downstream -- the bounding box, the mesh and the section survey --
    # reads these, never o.Shape, so a moved assembly is photographed
    # where it actually is.
    placed, moved = [], 0
    for o in solids:
        try:
            sh = o.Shape.copy()
            ch = chain(o)
            sh.Placement = ch.multiply(o.Placement)
            if ch.Base.Length > 1e-9 or ch.Rotation.Angle > 1e-9:
                moved += 1
            placed.append(sh)
        except BaseException:
            pass
    if not placed:
        finish("empty", reason="no readable shapes among the chosen solids")
    if moved:
        say("%d of %d solids sit inside a moved container; their "
            "placements are composed in" % (moved, len(placed)))

    bb = None
    for sh in placed:
        b = sh.BoundBox
        bb = b if bb is None else (bb.add(b) or bb)
    span = max(bb.XLength, bb.YLength, bb.ZLength) or 1.0
    say("extent %.0f x %.0f x %.0f mm" % (bb.XLength, bb.YLength, bb.ZLength))

    # --- one tessellation, reused for every image -------------------
    # --- fidelity: the decade the OPERATOR is thinking in -----------
    # One number for "the smallest detail worth seeing", in the decades an
    # engineer works in. It sets the mesh deviation AND the grid pitch,
    # because those are the same question asked twice.
    DECADES = [1e-3, 1e-2, 1e-1, 1.0, 10.0, 100.0, 1e3, 1e4, 1e5, 1e6]
    GRID_MAX_LINES = 120        # denser than this and you cannot count it
    GRID_MIN_LINES = 3          # sparser and it is not a reference
    MESH_MAX_SEGMENTS = 20000   # chord segments across the longest extent
    MESH_MIN_SEGMENTS = 20      # below this the mesh stops being the shape

    def fmt_mm(v):
        if v >= 1e6:
            return "%g km" % (v / 1e6)
        if v >= 1e3:
            return "%g m" % (v / 1e3)
        return "%g mm" % v

    def nearest_decade(v):
        lv = math.log10(max(float(v), 1e-9))
        return min(DECADES, key=lambda d2: abs(math.log10(d2) - lv))

    fid = float(job.get("fidelity", 0) or 0)
    fid_auto = fid <= 0
    if fid_auto:
        fid = nearest_decade(span / 200.0)
    else:
        fid = nearest_decade(fid)

    # The mesh deviation is the fidelity, coarsened by whole decades only
    # if this model at that fidelity would be absurd. Reported either way:
    # silently meshing at something other than what was asked is how
    # "Ultrafine" came to mean nothing.
    dev = fid
    dev_steps = 0
    while span / dev > MESH_MAX_SEGMENTS and dev < DECADES[-1]:
        dev *= 10.0
        dev_steps += 1
    # ...and refined if it is coarser than the model itself. A deviation
    # of 1 km on a 5 mm part is not a coarse mesh, it is a triangle: the
    # chord error is allowed to exceed the whole object. Asking for 1 km
    # fidelity on a small part is a reasonable thing for an operator to
    # do by accident, and it should not silently destroy the geometry.
    while span / dev < MESH_MIN_SEGMENTS and dev > DECADES[0]:
        dev /= 10.0
        dev_steps -= 1

    # The grid pitch is the fidelity, stepped by decades until it is
    # readable. Always a round decade, so a section can be measured off
    # the image without being told the pitch -- and stated anyway.
    gridmm = fid
    grid_steps = 0
    while span / gridmm > GRID_MAX_LINES and gridmm < DECADES[-1]:
        gridmm *= 10.0
        grid_steps += 1
    while span / gridmm < GRID_MIN_LINES and gridmm > DECADES[0]:
        gridmm /= 10.0
        grid_steps -= 1

    say("fidelity %s (%s)" % (fmt_mm(fid),
                              "auto, from model size" if fid_auto
                              else "operator"))
    if dev_steps > 0:
        say("  mesh coarsened %d decade(s) to %s: at %s this %s model "
            "would need over %d chord segments"
            % (dev_steps, fmt_mm(dev), fmt_mm(fid), fmt_mm(span),
               MESH_MAX_SEGMENTS))
    elif dev_steps < 0:
        say("  mesh refined %d decade(s) to %s: a %s deviation on a %s "
            "model allows a chord error bigger than the object"
            % (-dev_steps, fmt_mm(dev), fmt_mm(fid), fmt_mm(span)))
    if grid_steps > 0:
        say("  grid coarsened %d decade(s) to %s: a %s grid across %s is "
            "over %d lines and cannot be counted"
            % (grid_steps, fmt_mm(gridmm), fmt_mm(fid), fmt_mm(span),
               GRID_MAX_LINES))
    elif grid_steps < 0:
        say("  grid refined %d decade(s) to %s: a %s grid across %s gives "
            "fewer than %d lines, which is no reference at all"
            % (-grid_steps, fmt_mm(gridmm), fmt_mm(fid), fmt_mm(span),
               GRID_MIN_LINES))

    t = time.time()
    meshes = []
    for sh in placed:
        try:
            pts, facets = sh.tessellate(dev)
            if facets:
                meshes.append((pts, facets))
        except BaseException:
            pass
    nf = sum(len(f) for _, f in meshes)
    say("tessellated %d facets at deviation %.2f in %.0f ms"
        % (nf, dev, (time.time() - t) * 1000))

    def scene():
        root = coin.SoSeparator()
        # Three lights, not one. A single SoDirectionalLight points down
        # -Z by default, so slices viewed along X or Y came out almost
        # black -- which for a vision model is a wasted image, not a dim
        # one.
        for d, i in (((-0.4, -0.6, -1.0), 1.0),
                     ((0.8, -0.3, -0.5), 0.6),
                     ((0.2, 0.9, 0.3), 0.4)):
            lt = coin.SoDirectionalLight()
            lt.direction = d
            lt.intensity = i
            root.addChild(lt)
        mat = coin.SoMaterial()
        mat.diffuseColor = (0.78, 0.80, 0.84)
        root.addChild(mat)
        for pts, facets in meshes:
            sep = coin.SoSeparator()
            co = coin.SoCoordinate3()
            co.point.setValues(0, len(pts), [(p.x, p.y, p.z) for p in pts])
            sep.addChild(co)
            idx = []
            for f in facets:
                idx += [f[0], f[1], f[2], -1]
            fs = coin.SoIndexedFaceSet()
            fs.coordIndex.setValues(0, len(idx), idx)
            sep.addChild(fs)
            root.addChild(sep)
        return root

    def grid_node(normal, d, step):
        \"\"\"A scale reference at the cut plane. The whole reason an image is
        worth more than a number is that something in it has a known size.

        Nudged a hair onto the KEPT side rather than drawn exactly on the
        plane: n.P >= D keeps points at equality, but which way a vertex
        exactly on the clip plane rounds after transform is the GPU's
        business, so an on-plane grid can z-fight or vanish -- taking the
        one scale reference in the image with it.
        \"\"\"
        g = coin.SoSeparator()
        m = coin.SoMaterial()
        m.diffuseColor = (0.0, 0.74, 0.83)
        m.emissiveColor = (0.0, 0.74, 0.83)
        g.addChild(m)
        # Only as big as the model. An earlier version padded by a whole
        # grid step in every direction, and because viewAll() frames the
        # entire scene graph the subject ended up filling under a fifth of
        # the image -- most of the frame was empty background, which for a
        # vision model is tokens spent on nothing.
        lo = (bb.XMin, bb.YMin, bb.ZMin)
        hi = (bb.XMax, bb.YMax, bb.ZMax)
        ax = normal.index(1) if 1 in normal else 2
        u, v = [i for i in (0, 1, 2) if i != ax]
        pts, counts = [], []

        def P(a, b):
            q = [0.0, 0.0, 0.0]
            q[ax] = d
            q[u] = a
            q[v] = b
            return tuple(q)

        a = math.floor(lo[u] / step) * step
        while a <= hi[u]:
            pts += [P(a, lo[v]), P(a, hi[v])]
            counts.append(2)
            a += step
        b = math.floor(lo[v] / step) * step
        while b <= hi[v]:
            pts += [P(lo[u], b), P(hi[u], b)]
            counts.append(2)
            b += step
        co = coin.SoCoordinate3()
        co.point.setValues(0, len(pts), pts)
        g.addChild(co)
        ls = coin.SoLineSet()
        ls.numVertices.setValues(0, len(counts), counts)
        g.addChild(ls)
        return g

    def contour_node(stack, ax, at, span_):
        \"\"\"Every cached section outline for this axis, with the one at `at`
        called out.

        `stack` is [(position, [polyline, ...]), ...]. The current plane is
        drawn bright and the rest fade with distance, so an image reads as
        "this contour, among these" rather than as a heap of lines.
        \"\"\"
        g = coin.SoSeparator()
        if not stack:
            return g
        for pos, polys in stack:
            if not polys:
                continue
            here = abs(pos - at) < 1e-6
            far = min(1.0, abs(pos - at) / (span_ or 1.0))
            sep = coin.SoSeparator()
            m = coin.SoMaterial()
            if here:
                # the cut plane itself: white-hot, unmissable
                m.diffuseColor = (1.0, 1.0, 1.0)
                m.emissiveColor = (1.0, 1.0, 1.0)
            else:
                # fore and aft, dimming with distance. Amber aft (already
                # cut away) and cyan near, so the two directions are
                # distinguishable without a legend.
                lvl = max(0.12, 0.62 - 0.5 * far)
                if pos > at:
                    m.diffuseColor = (lvl, lvl * 0.62, 0.0)
                    m.emissiveColor = (lvl, lvl * 0.62, 0.0)
                else:
                    m.diffuseColor = (0.0, lvl * 0.78, lvl)
                    m.emissiveColor = (0.0, lvl * 0.78, lvl)
            sep.addChild(m)
            dr = coin.SoDrawStyle()
            dr.lineWidth = 3.0 if here else 1.0
            sep.addChild(dr)
            pts, counts = [], []
            for poly in polys:
                if len(poly) < 2:
                    continue
                pts += poly
                counts.append(len(poly))
            if not counts:
                continue
            co = coin.SoCoordinate3()
            co.point.setValues(0, len(pts), pts)
            sep.addChild(co)
            ls = coin.SoLineSet()
            ls.numVertices.setValues(0, len(counts), counts)
            sep.addChild(ls)
            g.addChild(sep)
        return g

    W, H = job.get("width", 1024), job.get("height", 768)
    step = gridmm
    say("grid %s, about %d lines across the model, requested image %dx%d"
        % (fmt_mm(step), int(span / step), W, H))

    def render(clip_normal, clip_d, name, with_grid=True, stack=None):
        root = coin.SoSeparator()
        cam = coin.SoOrthographicCamera()
        root.addChild(cam)
        if clip_normal is not None:
            # The clip goes in its OWN separator with the body. Coin scopes
            # a clip plane to the separator it sits in, and the contour
            # stack below has to survive outside it -- every outline fore
            # of d lies in the half-space this plane removes, and that is
            # precisely the half the operator asked to still be able to
            # see.
            solid = coin.SoSeparator()
            cp = coin.SoClipPlane()
            # Coin keeps the half-space where n.P >= D, so the normal
            # points at what SURVIVES. The camera sits on the positive
            # side of this axis looking back along it, so what has to
            # survive is the FAR side, P[ax] <= clip_d -- which is the
            # negated normal at the negated distance. Passing +e_ax with
            # D=-clip_d kept P[ax] >= -clip_d instead: the wanted
            # half-space mirrored about the origin. On a model spanning
            # x 0..300 that put every plane outside the solid, and six
            # slices came back as six copies of one uncut image.
            cp.plane = coin.SbPlane(
                coin.SbVec3f(*[-c for c in clip_normal]), float(-clip_d))
            solid.addChild(cp)
            solid.addChild(scene())
            root.addChild(solid)
        else:
            root.addChild(scene())
        # Portrait for a tall section, landscape for a wide one. A
        # 143 x 839 mm section forced into a 4:3 frame leaves most of the
        # image empty, and empty pixels still cost tokens to read.
        ax0 = clip_normal.index(1.0) if clip_normal else 2
        e = [bb.XLength, bb.YLength, bb.ZLength]
        uu, vv = [i for i in (0, 1, 2) if i != ax0]
        # Size the frame to the object's own proportions, not to a
        # landscape or portrait preset. A 143 x 839 mm section is nearly
        # 6:1; snapping it to 3:4 still left the frame four times wider
        # than the subject, and empty pixels cost the same tokens to read
        # as full ones. Clamped so a very long thin part cannot produce a
        # sliver nothing can see.
        long_px = max(W, H)
        ratio = (e[uu] or 1.0) / (e[vv] or 1.0)
        if ratio <= 1.0:
            h_px = long_px
            w_px = int(max(320, min(long_px, long_px * ratio * 1.25)))
        else:
            w_px = long_px
            h_px = int(max(320, min(long_px, long_px / ratio * 1.25)))
        w_px -= w_px % 4
        h_px -= h_px % 4
        vp = coin.SbViewportRegion(w_px, h_px)
        # Set the camera from the PROJECTED extent, not with viewAll().
        # viewAll() fits the bounding SPHERE, so this 143 x 192 x 839 mm
        # assembly viewed along its short axis was framed to its 860 mm
        # diagonal and the subject filled about a fifth of the image. For a
        # vision model that is four fifths of the pixels, and of the
        # tokens, spent on empty background.
        ax = clip_normal.index(1.0) if clip_normal else 2
        ext = [bb.XLength, bb.YLength, bb.ZLength]
        ctr = [(bb.XMin + bb.XMax) / 2.0, (bb.YMin + bb.YMax) / 2.0,
               (bb.ZMin + bb.ZMax) / 2.0]
        u, v = [i for i in (0, 1, 2) if i != ax]
        aspect = float(w_px) / float(h_px)
        height = max(ext[v], (ext[u] or 1.0) / aspect) * 1.12
        view = [0.0, 0.0, 0.0]
        view[ax] = -1.0
        dist = (ext[ax] or span) * 2.0 + span
        cam.position.setValue(
            coin.SbVec3f(*[ctr[i] - view[i] * dist for i in (0, 1, 2)]))
        # pointAt with an explicit UP vector. Setting only the direction,
        # with SbRotation(-Z, view), leaves the roll to Coin's
        # shortest-arc choice -- which put world +Z sideways, so a
        # vertical post came out lying on its side. An image whose "up" is
        # arbitrary is hard to read and worthless for comparing slices.
        up = (0.0, 1.0, 0.0) if ax == 2 else (0.0, 0.0, 1.0)
        cam.pointAt(coin.SbVec3f(*ctr), coin.SbVec3f(*up))
        cam.height.setValue(height)
        cam.nearDistance.setValue(0.01)
        cam.farDistance.setValue(dist * 4 + span * 4)
        if with_grid and clip_normal is not None:
            # kept side is P[ax] <= clip_d, so step back off the plane
            eps = max(span * 1e-4, 1e-4)
            root.addChild(grid_node(clip_normal, clip_d - eps, step))
        if stack and clip_normal is not None:
            root.addChild(contour_node(
                stack, clip_normal.index(1.0), clip_d, span))
        r = coin.SoOffscreenRenderer(vp)
        r.setBackgroundColor(coin.SbColor(0.09, 0.09, 0.14))
        if not r.render(root):
            return None
        # writeToFile is dead headless: getNumWriteFiletypes() is 0, no
        # image plugin is registered. The raw buffer works.
        img = Image.frombytes("RGB", (w_px, h_px),
                              bytes(r.getBuffer()))
        img = img.transpose(Image.FLIP_TOP_BOTTOM)
        p = os.path.join(OUT_DIR, name)
        img.save(p)
        return p

    made = []
    p = render(None, 0, "00_whole.png", with_grid=False)
    if p:
        made.append(p)
    say("whole-model view done")

    # --- the survey: where does the section change? -----------------
    # v4.0.10: all three axes by default. One family of parallel sections
    # shows you a stack of outlines; it does not let anything rebuild the
    # object. Three orthogonal families do.
    axes = job.get("axes") or ["x", "y", "z"]
    nslices = int(job.get("slices", 12))

    # makePlane's own normal is +Z, so rotate it onto the wanted axis and
    # translate so it covers the whole bbox. An earlier version made an XY
    # plane and then positioned it for a different axis, so every section
    # came back empty in a suspiciously fast 0.1 s.
    ROT = {0: App.Rotation(App.Vector(0, 1, 0), 90),
           1: App.Rotation(App.Vector(1, 0, 0), -90),
           2: App.Rotation()}

    # A straight edge needs 2 points; a circle needs more. 10 keeps a
    # 20 mm hole visibly round at 1024 px without turning the outline of a
    # busy section into tens of thousands of vertices.
    CONTOUR_POINTS = 10
    CONTOUR_MAX_POLYS = 600     # per plane, across all solids

    def survey(ai, positions):
        out = []
        shapes = []
        ctr = [(bb.XMin + bb.XMax) / 2.0, (bb.YMin + bb.YMax) / 2.0,
               (bb.ZMin + bb.ZMax) / 2.0]
        for d in positions:
            # Place by CENTRE, not by corner. makePlane puts its corner at
            # the origin and spans +X +Y; once rotated onto X or Y that
            # span points away from the model, so a corner computed from
            # the bbox minimum put the plane entirely outside it. Z looked
            # fine because its rotation is the identity -- which is why
            # only X and Y surveyed in a suspiciously fast 0.1 s with
            # nothing found.
            pl = Part.makePlane(span * 3, span * 3)
            pl.Placement = App.Placement(App.Vector(0, 0, 0), ROT[ai])
            c = pl.BoundBox.Center
            tgt = list(ctr)
            tgt[ai] = d
            pl.translate(App.Vector(tgt[0] - c.x, tgt[1] - c.y,
                                    tgt[2] - c.z))
            parts = regions = 0
            polys = []
            for sh2 in placed:
                try:
                    sec = sh2.section(pl)
                    if sec.Edges:
                        parts += 1
                        regions += len(sec.Wires) or 1
                        # Cache the outline as polylines, ONCE. Every image
                        # on this axis reuses them, so the cost is one
                        # section per plane, not one per plane per image.
                        for e in sec.Edges:
                            if len(polys) >= CONTOUR_MAX_POLYS:
                                break
                            try:
                                vs = e.discretize(Number=CONTOUR_POINTS)
                                polys.append([(v.x, v.y, v.z) for v in vs])
                            except BaseException:
                                try:
                                    vs = e.Vertexes
                                    if len(vs) >= 2:
                                        polys.append(
                                            [(v.Point.x, v.Point.y,
                                              v.Point.z) for v in vs])
                                except BaseException:
                                    pass
                except BaseException:
                    pass
            out.append({"at": round(d, 2), "parts": parts,
                        "regions": regions, "outline_polys": len(polys)})
            shapes.append((d, polys))
        return out, shapes

    profiles = {}
    second = []
    for axis in axes:
        ai = {"x": 0, "y": 1, "z": 2}[axis]
        normal = [0.0, 0.0, 0.0]
        normal[ai] = 1.0
        lo = (bb.XMin, bb.YMin, bb.ZMin)[ai]
        hi = (bb.XMax, bb.YMax, bb.ZMax)[ai]
        positions = [lo + (hi - lo) * (i + 0.5) / nslices
                     for i in range(nslices)]

        t = time.time()
        prof, stack = survey(ai, positions)
        profiles[axis] = prof
        say("%s: surveyed %d planes in %.1f s, %d outline polylines "
            "cached" % (axis, nslices, time.time() - t,
                        sum(len(p) for _, p in stack)))

        t = time.time()
        for i, d in enumerate(positions):
            pth = render(normal, d, "%s_%02d_%+.0f.png" % (axis, i + 1, d),
                         stack=stack)
            if pth:
                made.append(pth)
        say("%s: %d slice views in %.1f s"
            % (axis, nslices, time.time() - t))

        if job.get("second_degree"):
            scored = []
            for i in range(1, len(prof)):
                sc = (abs(prof[i]["regions"] - prof[i - 1]["regions"])
                      + 2 * abs(prof[i]["parts"] - prof[i - 1]["parts"]))
                if sc:
                    scored.append(
                        (sc, (prof[i]["at"] + prof[i - 1]["at"]) / 2.0))
            scored.sort(reverse=True)
            want = scored[:int(job.get("second_count", 4))]
            say("%s: second pass at %d planes" % (axis, len(want)))
            for k, (sc, d) in enumerate(want):
                pth = render(normal, d, "%s_2nd_%02d_%+.0f_score%d.png"
                             % (axis, k + 1, d, sc), stack=stack)
                if pth:
                    made.append(pth)
                    second.append({"axis": axis, "at": round(d, 2),
                                   "score": sc,
                                   "image": os.path.basename(pth)})


    finish("ok", images=[os.path.basename(x) for x in made],
           profiles=profiles, second_degree=second, facets=nf,
           extent=[round(bb.XLength, 1), round(bb.YLength, 1),
                   round(bb.ZLength, 1)],
           # So an agent reading a section does not have to guess the
           # pitch, or regex it out of the prose log.
           fidelity_mm=fid, fidelity_auto=fid_auto,
           deviation_mm=dev, grid_mm=step,
           grid_lines=int(span / step),
           fidelity_note=("grid stepped %+d decade(s) from the fidelity "
                          "for readability" % grid_steps) if grid_steps
                         else "grid pitch is the fidelity as asked")
except SystemExit:
    raise
except BaseException:
    LOG.append(traceback.format_exc())
    finish("error")
"""


def _freecadcmd_path():
    """FreeCADCmd beside this FreeCAD. Checked in both places it lives:
    the install root on this build, bin/ on others."""
    try:
        home = App.getHomePath()
    except BaseException:
        return ""
    exe = "FreeCADCmd.exe" if os.name == "nt" else "FreeCADCmd"
    for cand in (os.path.join(home, exe), os.path.join(home, "bin", exe)):
        if os.path.isfile(cand):
            return cand
    return ""


def start_capture(doc, out_dir, preset="Medium", slices=None,
                  axes=None, objects=None, second_degree=False,
                  second_count=4, fidelity=0.0, width=None, height=None):
    """Launch the capture worker. Returns (ok, message, job_dir).

    Returns as soon as the process is launched -- it does NOT wait. The
    caller polls for capture_manifest.json, because blocking here would
    undo the entire point of using another process.
    """
    exe = _freecadcmd_path()
    if not exe:
        return False, ("FreeCADCmd was not found beside this FreeCAD, so "
                       "capture cannot run in its own process."), ""
    fname = getattr(doc, "FileName", "") or ""
    if not fname or not os.path.isfile(fname):
        return False, ("Save the document first. The second process opens "
                       "it from disk, so unsaved work is not visible to "
                       "it."), ""
    p = CAPTURE_PRESETS.get(preset, CAPTURE_PRESETS["Medium"])
    job = {
        "doc": fname, "out_dir": out_dir,
        "slices": int(slices or p[0]), "grid_divisions": p[1],
        "width": int(width or p[2]), "height": int(height or p[3]),
        "deviation": p[4],
        # v4.0.19: 0 means let the worker pick the decade from the model's
        # own size. Anything else is the operator's decade, and the worker
        # clamps it by whole decades if it cannot suit this model.
        "fidelity": float(fidelity or 0.0),
        "axes": list(axes or ["x", "y", "z"]),
        "objects": list(objects or []),
        "second_degree": bool(second_degree),
        "second_count": int(second_count), "preset": preset,
    }
    try:
        os.makedirs(out_dir, exist_ok=True)
        wpath = os.path.join(out_dir, "_capture_worker.py")
        # v4.0.14: compile it first. CAPTURE_WORKER_SRC is a non-raw
        # triple-quoted literal, so one stray backslash added to the
        # worker is eaten by the OUTER literal and lands in the written
        # file as a real newline mid-string -- a SyntaxError in a process
        # whose stdout and stderr both go to DEVNULL. That presents as
        # five minutes of "Capturing..." and then nothing at all. One
        # line turns it into an immediate, accurate message.
        try:
            compile(CAPTURE_WORKER_SRC, "<capture_worker>", "exec")
        except SyntaxError as exc:
            return (False,
                    "The embedded capture worker will not compile (line "
                    "%s: %s). Nothing was launched."
                    % (exc.lineno, exc.msg), "")
        with open(wpath, "w", encoding="utf-8") as fh:
            fh.write(CAPTURE_WORKER_SRC)
        jpath = os.path.join(out_dir, "capture_job.json")
        with open(jpath, "w", encoding="utf-8") as fh:
            json.dump(job, fh, indent=2)
        man = os.path.join(out_dir, "capture_manifest.json")
        if os.path.exists(man):
            os.remove(man)          # so the poll cannot read a stale one
        env = dict(os.environ)
        env["CAPTURE_JOB"] = jpath
        subprocess.Popen([exe, wpath], env=env,
                         stdout=subprocess.DEVNULL,
                         stderr=subprocess.DEVNULL)
    except BaseException as exc:
        return False, "Could not launch the capture process: %s" % exc, ""
    return True, ("Capture running in a second FreeCAD process. Your "
                  "session is not affected."), out_dir


class IDEManager:
    """Detects and manages AI sources: IDEs (VS Code, Devin Desktop, Cursor, Zed,
    Claude Code) plus the local Ollama chat panel."""

    # IDE definitions: (display_name, cli_command, ai_assistant_name, common_install_paths)
    SUPPORTED_IDES = {
        'vscode': {
            'name': 'VS Code',
            'cli': 'code',
            'ai_name': 'GitHub Copilot / Continue',
            'paths_win': [
                os.path.expandvars(r'%LOCALAPPDATA%\Programs\Microsoft VS Code\bin\code.cmd'),
                os.path.expandvars(r'%PROGRAMFILES%\Microsoft VS Code\bin\code.cmd'),
            ]
        },
        'devin': {
            # v3.4.1: Cognition rebranded Windsurf to Devin Desktop on 2026-06-02
            # via an OTA update. The binary is now Devin.exe on Windows, so the
            # old 'windsurf' CLI probe silently reported "Not Found" on machines
            # that had simply been updated. Legacy names are kept as fallbacks
            # for anyone still on a pre-rename build.
            'name': 'Devin Desktop',
            'cli': 'devin',
            'cli_alt': ['windsurf'],
            'ai_name': 'Devin Local',
            'paths_win': [
                os.path.expandvars(r'%LOCALAPPDATA%\Programs\Devin\bin\devin.cmd'),
                os.path.expandvars(r'%LOCALAPPDATA%\Devin\bin\devin.cmd'),
                os.path.expandvars(r'%PROGRAMFILES%\Devin\bin\devin.cmd'),
                os.path.expandvars(r'%LOCALAPPDATA%\Programs\Devin\Devin.exe'),
                # legacy Windsurf install locations (pre-2026-06-02)
                os.path.expandvars(r'%LOCALAPPDATA%\Programs\Windsurf\bin\windsurf.cmd'),
                os.path.expandvars(r'%LOCALAPPDATA%\Windsurf\bin\windsurf.cmd'),
                os.path.expandvars(r'%PROGRAMFILES%\Windsurf\bin\windsurf.cmd'),
            ]
        },
        'ollama': {
            # v3.4.1: Ollama is NOT an editor - there is no application to
            # launch. It is a headless inference server on :11434. It appears
            # here so the dropdown answers one question consistently ("where
            # does my AI come from?"); selecting it turns the launch button
            # into "Open Chat" and opens the local chat panel instead.
            'name': 'Ollama (Local AI)',
            'cli': 'ollama',
            'ai_name': 'Local model',
            'is_local_chat': True,
            'paths_win': [
                os.path.expandvars(r'%LOCALAPPDATA%\Programs\Ollama\ollama.exe'),
                os.path.expandvars(r'%PROGRAMFILES%\Ollama\ollama.exe'),
            ]
        },
        'cursor': {
            'name': 'Cursor',
            'cli': 'cursor',
            'ai_name': 'Cursor AI',
            'paths_win': [
                os.path.expandvars(r'%LOCALAPPDATA%\Programs\cursor\cursor.exe'),
                os.path.expandvars(r'%LOCALAPPDATA%\cursor\cursor.exe'),
                os.path.expandvars(r'%PROGRAMFILES%\Cursor\cursor.exe'),
            ]
        },
        'zed': {
            'name': 'Zed',
            'cli': 'zed',
            'ai_name': 'Zed AI',
            # v5.0.19: no flags. Zed is not a VS Code fork and rejects
            # --reuse-window outright; its own reuse flag has been --reuse
            # and --existing in different builds. A bare folder opens on
            # every version.
            'launch_args': [],
            'paths_win': [
                os.path.expandvars(r'%LOCALAPPDATA%\Zed\zed.exe'),
                os.path.expandvars(r'%PROGRAMFILES%\Zed\zed.exe'),
            ]
        },
        'antigravity': {
            # v5.0.19: Google Antigravity, a VS Code fork (its own --help
            # lists -r/--reuse-window). Installed on the operator's machine
            # and unknown to this table until now. Reads AGENTS.md.
            # 'Antigravity IDE' is the current product (2.6.0, 2026-10);
            # plain 'Antigravity' (2.0.x) is the older install.
            'name': 'Antigravity',
            'cli': 'antigravity-ide',
            'cli_alt': ['antigravity'],
            'ai_name': 'Antigravity Agent',
            'paths_win': [
                os.path.expandvars(r'%LOCALAPPDATA%\Programs\Antigravity IDE\bin\antigravity-ide.cmd'),
                os.path.expandvars(r'%LOCALAPPDATA%\Programs\Antigravity IDE\Antigravity IDE.exe'),
                os.path.expandvars(r'%LOCALAPPDATA%\Programs\Antigravity\Antigravity.exe'),
            ]
        },
        'claude-code': {
            'name': 'Claude Code',
            'cli': 'claude',
            'ai_name': 'Claude',
            'paths_win': [
                os.path.expandvars(r'%APPDATA%\npm\claude.cmd'),
                os.path.expandvars(r'%LOCALAPPDATA%\npm\claude.cmd'),
                os.path.expandvars(r'%APPDATA%\npm\claude'),
            ]
        },
    }

    _detected_cache = None

    # ---- editors the operator adds themselves -------------------------
    # SUPPORTED_IDES above is a fixed table in this file. Before 3.5.0 that
    # meant an editor nobody here had heard of could not be used at all --
    # and on anyone else's machine the table is a guess. Custom entries live
    # in ai_config.json beside the rest of the Bridge's settings, so they
    # survive a restart and belong to the operator rather than to this file.
    CUSTOM_KEY_PREFIX = "custom:"

    @classmethod
    def _normalise_custom(cls, key, entry):
        """One stored entry, cleaned up, or None if it is unusable.

        Refusing a malformed entry here is the difference between an IDE that
        does not appear and a dropdown that raises while it is being built.
        """
        try:
            if not isinstance(entry, dict):
                return None
            name = str(entry.get("name") or "").strip()
            cli = str(entry.get("cli") or "").strip()
            path = str(entry.get("path") or "").strip()
            if not path:
                # A STORED entry keeps the path under 'paths_win' -- that is
                # what this method writes and what detection reads. Reading
                # only 'path' meant the full path was dropped the first time
                # the entry was loaded back, so an editor given a path
                # because its command is NOT on PATH stopped being found
                # after a restart, while the entry still looked right in
                # ai_config.json.
                existing = entry.get("paths_win") or []
                if isinstance(existing, str):
                    existing = [existing]
                path = str(existing[0] if existing else "").strip()
            if not name or not (cli or path):
                return None
            args = entry.get("args") or []
            if isinstance(args, str):
                args = args.split()
            key = str(key or "").strip()
            if not key.startswith(cls.CUSTOM_KEY_PREFIX):
                key = cls.CUSTOM_KEY_PREFIX + (key or name.lower())
            out = {
                "name": name,
                "cli": cli or os.path.basename(path),
                "ai_name": str(entry.get("ai_name")
                               or "the editor's own assistant"),
                "args": [str(a) for a in args],
                "custom": True,
            }
            if path:
                out["paths_win"] = [path]
            return key, out
        except BaseException:
            return None

    @classmethod
    def load_custom_ides(cls, config_file_path=None):
        """{key: entry} for every editor the operator added. Never raises."""
        path = config_file_path or AI_CONFIG_FILE
        try:
            if not os.path.exists(path):
                return {}
            with open(path, "r", encoding="utf-8") as fh:
                cfg = json.load(fh)
            out = {}
            for key, entry in (cfg.get("custom_ides") or {}).items():
                norm = cls._normalise_custom(key, entry)
                if norm is not None:
                    out[norm[0]] = norm[1]
            return out
        except BaseException as exc:
            App.Console.PrintWarning(
                "[IDE] Could not read custom editors from %s: %s\n"
                % (path, exc))
            return {}

    @classmethod
    def all_ides(cls):
        """The built-in table plus the operator's own entries. A built-in
        wins a key clash, so a bad custom entry cannot shadow Ollama."""
        merged = dict(cls.load_custom_ides())
        merged.update(cls.SUPPORTED_IDES)
        return merged

    @classmethod
    def add_custom_ide(cls, name, cli="", path="", args="",
                       config_file_path=None):
        """Store one editor. Returns (ok, message)."""
        cfg_path = config_file_path or AI_CONFIG_FILE
        norm = cls._normalise_custom(
            None, {"name": name, "cli": cli, "path": path, "args": args})
        if norm is None:
            return False, ("An editor needs a name, and either a command "
                           "that is on your PATH or the full path to its "
                           "executable.")
        key, entry = norm
        try:
            cfg = {}
            if os.path.exists(cfg_path):
                with open(cfg_path, "r", encoding="utf-8") as fh:
                    cfg = json.load(fh) or {}
            customs = cfg.get("custom_ides") or {}
            replaced = key in customs
            customs[key] = entry
            cfg["custom_ides"] = customs
            os.makedirs(os.path.dirname(cfg_path), exist_ok=True)
            with open(cfg_path, "w", encoding="utf-8") as fh:
                json.dump(cfg, fh, indent=2)
        except BaseException as exc:
            return False, "Could not write %s: %s" % (cfg_path, exc)
        cls.refresh_detection()
        found, where = cls.probe(entry.get("cli"),
                                 (entry.get("paths_win") or [""])[0])
        return True, ("%s %s.\n%s"
                      % (entry["name"],
                         "updated" if replaced else "added",
                         ("Found at %s." % where) if found else
                         ("Not found on this system yet. The entry is saved; "
                          "it will work once the editor is installed or the "
                          "path is corrected.")))

    @classmethod
    def remove_custom_ide(cls, key, config_file_path=None):
        """Forget one operator-added editor. Returns (ok, message)."""
        cfg_path = config_file_path or AI_CONFIG_FILE
        if not str(key).startswith(cls.CUSTOM_KEY_PREFIX):
            return False, ("%s is built into this macro and cannot be "
                           "removed." % key)
        try:
            if not os.path.exists(cfg_path):
                return False, "Nothing stored yet."
            with open(cfg_path, "r", encoding="utf-8") as fh:
                cfg = json.load(fh) or {}
            customs = cfg.get("custom_ides") or {}
            if key not in customs:
                return False, "%s is not in the stored list." % key
            name = (customs[key] or {}).get("name", key)
            del customs[key]
            cfg["custom_ides"] = customs
            with open(cfg_path, "w", encoding="utf-8") as fh:
                json.dump(cfg, fh, indent=2)
        except BaseException as exc:
            return False, "Could not write %s: %s" % (cfg_path, exc)
        cls.refresh_detection()
        return True, "%s removed." % name

    @staticmethod
    def probe(cli="", path=""):
        """Is this editor actually here? Returns (found, where).

        The same two questions detection asks, exposed on its own so the Add
        IDE tab can answer before anything is saved -- a stored entry that
        silently never resolves is the thing this mechanism exists to avoid.
        """
        import shutil as _sh
        try:
            if path and os.path.exists(path):
                return True, path
            if cli:
                hit = _sh.which(cli)
                if hit:
                    return True, hit
        except BaseException:
            pass
        return False, ""

    @classmethod
    def detect_installed_ides(cls):
        """Detect which IDEs are installed on this system"""
        if cls._detected_cache is not None:
            return cls._detected_cache

        import shutil
        detected = {}

        for ide_key, ide_info in cls.all_ides().items():
            # Check if CLI command is in PATH (v3.4.1: plus any legacy aliases,
            # so a renamed product like Windsurf->Devin still resolves)
            cli_path = None
            for cli_name in [ide_info['cli']] + list(ide_info.get('cli_alt', [])):
                cli_path = shutil.which(cli_name)
                if cli_path:
                    break
            if cli_path:
                detected[ide_key] = {
                    'path': cli_path,
                    'source': 'PATH',
                    **ide_info
                }
                continue

            # Check common install locations (Windows)
            for install_path in ide_info.get('paths_win', []):
                if os.path.exists(install_path):
                    detected[ide_key] = {
                        'path': install_path,
                        'source': 'install_dir',
                        **ide_info
                    }
                    break

        cls._detected_cache = detected
        return detected

    @classmethod
    def refresh_detection(cls):
        """Force re-detection of IDEs"""
        cls._detected_cache = None
        return cls.detect_installed_ides()

    @classmethod
    def get_ide_list_for_display(cls):
        """Return list of (ide_key, display_name) for GUI dropdown"""
        detected = cls.detect_installed_ides()
        every = cls.all_ides()
        result = []

        # v3.4.1: Ollama listed first - it's the offline option and needs no
        # external application. 'windsurf' key is gone (now 'devin').
        # v3.5.0: this walked the preferred list ALONE, so an editor added to
        # the table -- or by the operator -- never reached the dropdown at
        # all. The preferred keys keep their established order; everything
        # else follows.
        preferred = ['ollama', 'vscode', 'devin', 'cursor', 'zed',
                     'antigravity', 'claude-code']
        order = [k for k in preferred if k in every]
        order += [k for k in sorted(every) if k not in preferred]

        for ide_key in order:
            ide_info = every[ide_key]
            name = ide_info.get('name', ide_key)
            if ide_key.startswith(cls.CUSTOM_KEY_PREFIX):
                name += " (yours)"
            tag = "Installed" if ide_key in detected else "Not Found"
            result.append((ide_key, f"{name} [{tag}]"))

        return result

    # Path to the AI Bridge Workspace (contains .windsurfrules, .cursorrules, etc.)
    WORKSPACE_DIR = os.path.join(
        os.path.dirname(os.path.dirname(os.path.abspath(__file__))),
        'Macro_03', 'Technical_Data', 'AI_Bridge_Workspace'
    )
    WORKSPACE_HELPER_SOURCE = os.path.join(
        os.path.dirname(os.path.dirname(os.path.abspath(__file__))),
        'Macro_03', 'Technical_Data', 'AI_Bridge_Technical_Data', 'Tools', 'send_to_freecad.py'
    )

    @classmethod
    def launch_ide(cls, ide_key, workspace_dir=None):
        """Launch the specified IDE, opening the AI Bridge Workspace folder.
        The workspace contains rules files and helper tools that automatically
        instruct the AI assistant how to communicate with FreeCAD.
        Returns (success: bool, message: str)
        """
        import subprocess

        detected = cls.detect_installed_ides()

        # v3.4.1: Ollama is a local inference server, not an editor. There is
        # nothing to launch - selecting it opens the built-in chat panel. This
        # is handled BEFORE the detection check because the chat panel is still
        # useful (and will offer to start the server) even if the ollama CLI
        # isn't on PATH.
        if cls.all_ides().get(ide_key, {}).get('is_local_chat'):
            dialog = show_ollama_chat()
            if dialog is None:
                return False, ("Could not open the Ollama chat panel.\n"
                               "Check Config.OLLAMA_ENABLED and the Report View.")
            return True, ("Ollama chat panel opened.\n"
                          "The local model talks to FreeCAD through this same bridge.")

        if ide_key not in detected:
            every = cls.all_ides()
            ide_name = every.get(ide_key, {}).get('name', ide_key)
            # v3.5.0: this indexed SUPPORTED_IDES directly, which raises a
            # KeyError for an operator-added editor -- on the one code path
            # that runs when it is not found, i.e. exactly when it matters.
            cli_name = every.get(ide_key, {}).get('cli', ide_key)
            return False, (
                f"{ide_name} not found on this system.\n\n"
                f"Install it and ensure '{cli_name}' is in your PATH,\n"
                f"or give its full path in the Add IDE tab."
            )

        ide = detected[ide_key]
        ws = workspace_dir or cls.WORKSPACE_DIR

        # Ensure workspace exists
        if not os.path.isdir(ws):
            os.makedirs(ws, exist_ok=True)

        # Claude Code: open a terminal window running 'claude' in the workspace dir
        # (reads CLAUDE.md automatically from the working directory)
        if ide_key == 'claude-code':
            try:
                # v5.0.19: the terminal STARTS in the workspace (cwd=) rather
                # than being told to `cd /d "<ws>" && claude`. subprocess
                # escaped those quotes as \" for cmd.exe, which does not read
                # \" as an escape, so cd failed with "The filename, directory
                # name, or volume label syntax is incorrect" and the && never
                # ran claude -- while this returned True. `start` passes its
                # working directory to the window it opens. The first quoted
                # argument to start is the window title.
                subprocess.Popen(
                    ['cmd', '/c', 'start', 'Claude Code', 'cmd', '/k',
                     'claude'],
                    cwd=ws
                )
                return True, (
                    "Claude Code launched in AI Bridge Workspace.\n"
                    "Claude will auto-read CLAUDE.md and know how to control FreeCAD."
                )
            except Exception as e:
                return False, f"Error launching Claude Code: {str(e)}"

        # Open the FOLDER so the IDE reads its rules file (AGENTS.md,
        # .cursorrules, .windsurfrules, CLAUDE.md, copilot-instructions).
        # v3.5.0: an editor the operator added themselves may reject an
        # unknown option and refuse to start, so a custom entry passes only
        # the arguments it was given.
        # v5.0.19: built-ins carry their own 'launch_args' too. Every one got
        # the VS Code family's --reuse-window, which Zed rejects ("unexpected
        # argument") and then opens nothing.
        if ide.get('custom'):
            extra = list(ide.get('args') or [])
        else:
            extra = list(ide.get('launch_args', ['--reuse-window']))
        cmd = [ide['path']] + extra + [ws]

        try:
            import tempfile
            import time as _t
            errf = tempfile.TemporaryFile()
            proc = subprocess.Popen(cmd, shell=True,
                                    stdout=subprocess.DEVNULL, stderr=errf)
            # v5.0.19: Popen returning only means a process STARTED. Zed
            # printed its usage error and exited while this reported
            # "launched". Editors hand off to a running instance and exit 0,
            # or keep running; a non-zero exit inside this window is a
            # launcher that refused, and the operator is told what it said.
            deadline = _t.time() + 2.0
            while _t.time() < deadline and proc.poll() is None:
                _t.sleep(0.1)
            rc = proc.poll()
            if rc not in (None, 0):
                try:
                    errf.seek(0)
                    said = errf.read().decode('utf-8', 'replace').strip()
                except Exception:
                    said = ''
                return False, (
                    f"{ide['name']} refused to start (exit code {rc}).\n"
                    + (f"It said: {said[:400]}" if said else
                       "It printed nothing.")
                    + f"\n\nCommand: {' '.join(cmd)}")
            return True, (
                f"{ide['name']} launched with AI Bridge Workspace.\n"
                f"The AI assistant will auto-read the rules file and know how to control FreeCAD."
            )
        except Exception as e:
            return False, f"Error launching {ide['name']}: {str(e)}"

    @classmethod
    def sync_workspace_bridge_files(cls, io_dir):
        """Ensure the AI Bridge Workspace contains the helper files AI clients expect."""
        try:
            os.makedirs(cls.WORKSPACE_DIR, exist_ok=True)
        except Exception as e:
            App.Console.PrintWarning(f"[IDE] Could not create workspace directory: {e}\n")
            return

        helper_dest = os.path.join(cls.WORKSPACE_DIR, 'send_to_freecad.py')
        if os.path.exists(cls.WORKSPACE_HELPER_SOURCE):
            try:
                with open(cls.WORKSPACE_HELPER_SOURCE, 'r', encoding='utf-8') as f:
                    helper_text = f.read()

                # Bridge status now publishes last_heartbeat; keep the workspace helper aligned.
                helper_text = helper_text.replace(
                    "ts = status.get('timestamp', '')",
                    "ts = status.get('last_heartbeat') or status.get('timestamp', '')"
                )

                with open(helper_dest, 'w', encoding='utf-8') as f:
                    f.write(helper_text)
            except Exception as e:
                App.Console.PrintWarning(f"[IDE] Could not sync send_to_freecad.py: {e}\n")
        else:
            App.Console.PrintWarning(
                f"[IDE] Helper script not found: {cls.WORKSPACE_HELPER_SOURCE}\n"
            )

        context_src = os.path.join(io_dir, 'ai_ide_command.txt')
        context_dest = os.path.join(cls.WORKSPACE_DIR, 'ai_ide_command.txt')
        if os.path.exists(context_src):
            try:
                shutil.copy2(context_src, context_dest)
            except Exception as e:
                App.Console.PrintWarning(f"[IDE] Could not sync ai_ide_command.txt: {e}\n")

    @classmethod
    def generate_context_file(cls, ide_key, io_dir, learning_dir):
        """Generate a universal context instruction file for any IDE's AI assistant.
        Returns the path to the generated file.
        """
        ide_info = cls.SUPPORTED_IDES.get(ide_key, cls.SUPPORTED_IDES['vscode'])
        ai_name = ide_info.get('ai_name', 'AI Assistant')

        context_file = os.path.join(io_dir, "ai_ide_command.txt")

        context_instruction = """INSTRUCTIONS FOR AI ASSISTANT ({ai_name}):
======================================================================
Imagineering FreeCAD AI Bridge - Universal IDE Connection
======================================================================

**MANDATORY FIRST STEP - REGISTRATION HANDSHAKE (bridge v3.4.0+)**
======================================================================
This bridge will REJECT execute/run_macro commands from an agent that has
not registered. Before sending any command, append this line to the input
file ({input_file}):

   {{"id": "<uuid>", "type": "hello", "agent_id": "<your name>"}}

The bridge replies with a 'registration_ack' containing a context_hash.
Include that context_hash on every subsequent command. If you ever receive
a 'registration_required' response, the knowledge base has changed - re-read
the context summary below and send 'hello' again.

IMPORTANT: A context summary has been auto-generated for you!

FIRST, review this summary file:
   {context_summary}

This file contains:
- Recent successful command patterns (last 10)
- Common FreeCAD API patterns
- Error handling tips
- Links to full documentation

THEN, review these detailed resources:

1. Learning Database (successful command patterns):
   {learning_db}

Reference documents, all in:
   {tech_data}

2. FreeCAD Macro Compatibility Guide (1752 lines):
   README.txt
   - QDockWidget patterns for GUI development
   - PySide compatibility layers
   - 34-point compatibility checklist

3. Macro Collection Index (1210 lines):
   INDEX.txt
   - 46 production macros
   - Australian steel profiles (AS/NZS standards)
   - Parametric geometry tools

4. FreeCAD Expressions Reference:
   Expressions_Reference.txt
   - Parametric design with expressions
   - Unit handling and gotchas
   - Vector/matrix functions, conditionals

======================================================================
HOW TO SEND COMMANDS TO FREECAD:
======================================================================

The AI Bridge uses a file-based protocol. To execute FreeCAD Python commands:

INPUT FILE:  {input_file}
OUTPUT FILE: {output_file}
STATUS FILE: {status_file}

EASIEST: the helper in your workspace does the handshake for you
   python send_to_freecad.py --status
   python send_to_freecad.py "print(App.ActiveDocument)"

DOING IT BY HAND - every command carries agent_id AND the context_hash
from YOUR registration_ack. Leave either out and the reply is
"registration_required" instead of a result.

POWERSHELL COMMAND PATTERN (set $hash from your registration_ack first):
$input_file = "{input_file}"
$hash = "PASTE_CONTEXT_HASH_FROM_YOUR_ACK"
$cmd = '{{"id":"' + (New-Guid) + '","agent_id":"YOUR_NAME","context_hash":"' + $hash + '","timestamp":"' + (Get-Date -Format o) + '","command":"YOUR_PYTHON_COMMAND","description":"What it does"}}'
Add-Content -Path $input_file -Value $cmd -NoNewline; Add-Content -Path $input_file -Value "`n"

BASH/TERMINAL COMMAND PATTERN (set HASH from your registration_ack first):
INPUT_FILE="{input_file}"
HASH="PASTE_CONTEXT_HASH_FROM_YOUR_ACK"
echo '{{"id":"'$(date +%s%N)'","agent_id":"YOUR_NAME","context_hash":"'$HASH'","timestamp":"'$(date -Iseconds)'","command":"YOUR_PYTHON_COMMAND","description":"What it does"}}' >> "$INPUT_FILE"

The hash changes after commands that modify the document. When a reply
is "registration_required", send "hello" again and use the NEW hash.

PARAMETRIC MEMORY AND MULTICORE (Bridge 5.0.17+):
   print(AIBridge.help())     lists memory_recall/start/note/checkpoint,
                              inventory, capture (runs in a second process)

WORKFLOW:
1. Send ONE command at a time
2. WAIT for result in ai_output_results.jsonl (check timestamp!)
3. VERIFY success before sending next command
4. If command fails, FIX it - don't send variations repeatedly

CHARACTER ENCODING:
- DO NOT use special characters in commands (no degree symbol, no micro, no plus-minus)
- Use ASCII alternatives: 'deg' instead of degree, 'micro' instead of mu

After reviewing these files, you will be equipped to:
- Generate FreeCAD commands with proven patterns
- Suggest fixes when commands fail by referencing past successes
- Create proper dockable GUI interfaces
- Reference existing macro examples
- Understand the user's workflow and preferences

Type "Ready" when you've reviewed these files.
""".format(
            ai_name=ai_name,
            context_summary=os.path.join(io_dir, 'ai_context_summary.txt'),
            learning_db=os.path.join(learning_dir, 'AI_Learning_Database.json'),
            input_file=os.path.join(io_dir, 'ai_input_commands.jsonl'),
            output_file=os.path.join(io_dir, 'ai_output_results.jsonl'),
            status_file=os.path.join(io_dir, 'ai_status.json'),
            # v5.0.14: resolved on THIS machine from the operator's own
            # Locations setting, not a path typed into the source. The
            # literals that used to be here named one person's Desktop
            # and were wrong everywhere else.
            tech_data=library_dir(),
        )

        with open(context_file, 'w', encoding='utf-8') as f:
            f.write(context_instruction)

        return context_file

    @classmethod
    def get_saved_preference(cls, config_file_path):
        """Load the user's preferred IDE from config"""
        try:
            if os.path.exists(config_file_path):
                with open(config_file_path, 'r') as f:
                    config = json.load(f)
                    saved = config.get('preferred_ide', 'vscode')
                    # v3.4.1: 'windsurf' key retired when the product became
                    # Devin Desktop - migrate silently so an existing config
                    # doesn't fall back to VS Code without explanation.
                    if saved == 'windsurf':
                        saved = 'devin'
                    if saved not in cls.SUPPORTED_IDES:
                        saved = 'vscode'
                    return saved
        except Exception:
            pass
        return 'vscode'

    @classmethod
    def save_preference(cls, config_file_path, ide_key):
        """Save the user's preferred IDE to config"""
        try:
            config = {}
            if os.path.exists(config_file_path):
                with open(config_file_path, 'r') as f:
                    config = json.load(f)
            config['preferred_ide'] = ide_key
            with open(config_file_path, 'w') as f:
                json.dump(config, f, indent=2)
        except Exception:
            pass

# Suppress Qt font warnings
os.environ['QT_LOGGING_RULES'] = '*.debug=false;qt.qpa.fonts=false'

# Import Qt
try:
    from PySide2 import QtCore, QtWidgets, QtGui
    from PySide2.QtCore import Qt
    QtCore.qInstallMessageHandler(lambda msg_type, context, message: None)
except ImportError:
    try:
        from PySide import QtCore, QtGui
        from PySide.QtCore import Qt
        QtWidgets = QtGui
        QtCore.qInstallMessageHandler(lambda msg_type, context, message: None)
    except ImportError:
        App.Console.PrintError("PySide/PySide2 not available - GUI will not work\n")
        QtCore = QtWidgets = QtGui = None

# ============================================================
# DIRECTORY CONFIGURATION - PORTABLE PATHS
# ============================================================

def get_ai_io_dir():
    """Get AI I/O directory with proper fallback"""
    # Try config file first
    config_file = os.path.join(App.getUserAppDataDir(), "ai_bridge_config.json")
    if os.path.exists(config_file):
        try:
            config = _read_config_strict(config_file)
            custom_dir = config.get('io_dir')
            if custom_dir and os.path.isabs(custom_dir):
                return custom_dir
        except Exception as e:
            App.Console.PrintWarning(
                f"AI Bridge: ai_bridge_config.json unreadable ({e}) - using the DEFAULT IO dir, NOT your configured one\n")
            pass
    
    # Default to FreeCAD user data directory
    return os.path.join(App.getUserAppDataDir(), "AI_Agent_IO")

def get_learning_dir():
    """Get learning directory with proper fallback"""
    # Try config file first
    config_file = os.path.join(App.getUserAppDataDir(), "ai_bridge_config.json")
    if os.path.exists(config_file):
        try:
            config = _read_config_strict(config_file)
            custom_dir = config.get('learning_dir')
            if custom_dir and os.path.isabs(custom_dir):
                return custom_dir
        except Exception as e:
            App.Console.PrintWarning(
                f"AI Bridge: ai_bridge_config.json unreadable ({e}) - using the DEFAULT learning dir, NOT your configured one\n")
            pass
    
    # v4.0.05: ai_config.json is what the Locations tab writes, so it has
    # the first say. The ai_bridge_config.json read above stays as a legacy
    # fallback for an install that has one.
    try:
        # v4.0.11: the FIRST entry is the one written to. Any others are
        # read-only sources -- see learning_sources(). That is what lets
        # 226 entries in one database and 14 in another both count,
        # instead of the operator having to abandon one.
        chosen = _cfg_list("learning_dir")
        if chosen:
            return os.path.normpath(chosen[0])
    except BaseException:
        pass

    # Default to subdirectory in FreeCAD user data
    return os.path.join(App.getUserAppDataDir(), "AI_Learning")

# AI Agent I/O Configuration
AI_IO_DIR = get_ai_io_dir()
AI_INPUT_FILE = os.path.join(AI_IO_DIR, "ai_input_commands.jsonl")
AI_OUTPUT_FILE = os.path.join(AI_IO_DIR, "ai_output_results.jsonl")

# --- shared wire envelope (HQ/41_AI_Bridge/10_Core/wire.py) ---------------
# OPTIONAL. Only the author's machine has this folder; everywhere else the
# import is skipped and the Bridge runs on its built-in wire format.
# SOFT import, deliberately unlike the other five bridges, which assert.
# This macro is the operator's most-used tool and runs INSIDE FreeCAD: a hard
# ImportError here would take FreeCAD's bridge down over a path problem. The
# client-side shim in 50_Clients/bridge_client.py already normalises this
# bridge's dialect (verified against all 549 lines of its outbox), so a failed
# import degrades to "wire 1 plus client-side upgrade" rather than to nothing.
_wire_mod = None
try:
    _wire_core = os.path.join(os.path.expanduser("~"), "Desktop", "HQ",
                              "41_AI_Bridge", "10_Core")
    if os.path.isfile(os.path.join(_wire_core, "wire.py")):
        if _wire_core not in sys.path:
            sys.path.insert(0, _wire_core)
        import wire as _wire_mod
except Exception as _e:                       # noqa: BLE001
    App.Console.PrintWarning(
        "AI Bridge: shared wire contract unavailable (%s); emitting wire 1 "
        "and relying on client-side normalisation.\n" % _e)


# Same source, same defensive posture, and for the same reason: a hard
# ImportError here would take the operator's most-used tool down over a path
# problem. Without it the config loaders still fall back to a BOM-tolerant
# read, which is the repair that actually matters on this machine.
_res_mod = None
try:
    if os.path.isfile(os.path.join(_wire_core, "resilience.py")):
        import resilience as _res_mod
except Exception as _e:                       # noqa: BLE001
    App.Console.PrintWarning(
        "AI Bridge: shared resilience module unavailable (%s); config reads "
        "fall back to BOM-tolerant parsing.\n" % _e)


def _read_config_strict(config_file):
    """Read a bridge config, repairing safe damage and refusing the rest.

    Returns a dict or raises. Never returns {} for a damaged file: a config
    that cannot be read is an error the operator must see, not a silent
    downgrade to defaults nobody chose.
    """
    if _res_mod is not None:
        return _res_mod.load_json_repairing(config_file)
    # Fallback: utf-8-sig at minimum. Set-Content writes a BOM by default and
    # a bare open() rejects it.
    with open(config_file, 'r', encoding='utf-8-sig') as fh:
        return json.load(fh)


def _conform(entry):
    """Upgrade one outbox entry to the wire-2 envelope, if wire.py is present.

    FreeCAD had the deepest dialect of the six: no `id` at any level a generic
    reader looks at (it lived at content.command_id), success as a bool at
    content.success, and the payload nested under `content`. The measured
    consequence was that no non-model client could match a response to the
    command that caused it.
    """
    if _wire_mod is None:
        return entry
    try:
        return _wire_mod.upgrade(entry, "freecad", Config.VERSION)
    except Exception:                          # noqa: BLE001
        return entry                           # never lose a result to a bug here

AI_REPORT_FILE = os.path.join(AI_IO_DIR, "ai_report_view.jsonl")
AI_SELECTION_FILE = os.path.join(AI_IO_DIR, "ai_selection_view.jsonl")
AI_STATUS_FILE = os.path.join(AI_IO_DIR, "ai_status.json")
AI_CONFIG_FILE = os.path.join(AI_IO_DIR, "ai_config.json")
HEALTH_CHECK_FILE = os.path.join(AI_IO_DIR, "health_check.json")
ERROR_LOG_FILE = os.path.join(AI_IO_DIR, "error_log.txt")
PROCESSED_IDS_FILE = os.path.join(AI_IO_DIR, "processed_command_ids.json")

# AI Learning System Configuration
LEARNING_DIR = get_learning_dir()
LEARNING_DB_FILE = os.path.join(LEARNING_DIR, "AI_Learning_Database.json")

# ============================================================
# GLOBAL STATE - Thread-Safe
# ============================================================

class MonitorState:
    """Thread-safe monitoring state"""
    def __init__(self):
        self._lock = threading.RLock()
        self._monitoring_active = False
        self._last_position = 0
        self._commands_processed = 0
        self._errors_count = 0
        self._consecutive_errors = 0
        self._last_command_time = None
        self._start_time = None
        self._last_input_mtime = 0
        self._processed_command_ids = set()  # Track processed command IDs
        self._command_timestamps = {}  # Track command execution timestamps
        self._last_command_hash = None  # Track last command content hash
        self._recent_command_hashes = {}  # Track recent command hashes with timestamps
        # v3.4.0 Phase 8: agent registration handshake
        # {agent_id: context_hash} - an agent must say hello and receive the
        # current knowledge context before it may execute anything.
        self._registered_agents = {}
        self._load_processed_ids()

    # ---- v3.4.0: agent registration ----

    def register_agent(self, agent_id, context_hash):
        """Record that an agent has been handed the current context."""
        if not agent_id:
            return False
        with self._lock:
            self._registered_agents[agent_id] = context_hash
        return True

    def is_agent_registered(self, agent_id, current_hash=None):
        """True only if the agent registered AND holds the current context.

        When the knowledge base changes the hash changes, every registration
        goes stale, and agents are forced to re-read. That solves the
        'Claude read the rules three days ago' drift problem too.
        """
        if not agent_id:
            return False
        with self._lock:
            held = self._registered_agents.get(agent_id)
        if held is None:
            return False
        if current_hash is None:
            return True
        return held == current_hash

    def get_registered_agents(self):
        with self._lock:
            return dict(self._registered_agents)

    def clear_registrations(self):
        with self._lock:
            self._registered_agents.clear()

    @property
    def monitoring_active(self):
        with self._lock:
            return self._monitoring_active
    
    @monitoring_active.setter
    def monitoring_active(self, value):
        with self._lock:
            self._monitoring_active = value
            if value and self._start_time is None:
                self._start_time = datetime.now()
    
    @property
    def last_position(self):
        with self._lock:
            return self._last_position
    
    @last_position.setter
    def last_position(self, value):
        with self._lock:
            self._last_position = value
    
    def increment_commands(self):
        with self._lock:
            self._commands_processed += 1
            self._last_command_time = datetime.now()
            return self._commands_processed
    
    def increment_errors(self):
        with self._lock:
            self._errors_count += 1
            self._consecutive_errors += 1
            return self._errors_count
    
    def reset_consecutive_errors(self):
        with self._lock:
            self._consecutive_errors = 0

    def reset_session(self):
        """Reset per-session runtime stats for a clean monitoring restart."""
        with self._lock:
            self._commands_processed = 0
            self._errors_count = 0
            self._consecutive_errors = 0
            self._last_command_time = None
            self._last_position = 0
            self._last_input_mtime = 0
            self._last_command_hash = None
            self._recent_command_hashes = {}
            self._start_time = None
    
    @property
    def consecutive_errors(self):
        with self._lock:
            return self._consecutive_errors
    
    def is_command_processed(self, command_id):
        """Check if command ID has been processed"""
        with self._lock:
            return command_id in self._processed_command_ids
    
    def is_command_hash_recent(self, command_hash):
        """Check if command content hash was recently processed (prevents duplicate execution of same command)"""
        with self._lock:
            return command_hash in self._recent_command_hashes
    
    def mark_command_processed(self, command_id, command_hash=None, flush_immediate=True):
        """Mark command ID as processed with immediate flush option and track hash"""
        with self._lock:
            self._processed_command_ids.add(command_id)
            
            # Track command hash to prevent duplicate execution
            if command_hash:
                self._recent_command_hashes[command_hash] = datetime.now()
                # Clean old hashes — 30 second window (not 5 min!)
                # A 5-min window silently drops legitimate repeated commands
                # like recompute(), fitAll(), or iterative adjustments.
                cutoff = datetime.now() - timedelta(seconds=30)
                self._recent_command_hashes = {
                    h: t for h, t in self._recent_command_hashes.items()
                    if t > cutoff
                }
            # Keep only last 1000 IDs to prevent memory growth
            # NOTE: sets have no guaranteed order, so we track insertion
            # order via _processed_id_order (a list) to evict oldest first.
            if not hasattr(self, '_processed_id_order'):
                self._processed_id_order = list(self._processed_command_ids)
            self._processed_id_order.append(command_id)
            if len(self._processed_command_ids) > 1000:
                # Remove oldest 200 IDs (true FIFO via ordered list)
                to_remove = self._processed_id_order[:200]
                self._processed_id_order = self._processed_id_order[200:]
                for old_id in to_remove:
                    self._processed_command_ids.discard(old_id)
            # Save to disk IMMEDIATELY for critical commands
            if flush_immediate:
                self._save_processed_ids()
                # Force file system sync
                try:
                    if os.path.exists(PROCESSED_IDS_FILE):
                        with open(PROCESSED_IDS_FILE, 'r') as f:
                            f.read(1)  # Force OS to flush
                except:
                    pass
    
    def _load_processed_ids(self):
        """Load processed command IDs from disk"""
        try:
            if os.path.exists(PROCESSED_IDS_FILE):
                with open(PROCESSED_IDS_FILE, 'r') as f:
                    data = json.load(f)
                    self._processed_command_ids = set(data.get('ids', []))
                    App.Console.PrintMessage(f"[INIT] Loaded {len(self._processed_command_ids)} processed command IDs\n")
        except Exception as e:
            App.Console.PrintWarning(f"Could not load processed IDs: {e}\n")
    
    def _save_processed_ids(self):
        """Save processed command IDs to disk"""
        try:
            with open(PROCESSED_IDS_FILE, 'w') as f:
                json.dump({'ids': list(self._processed_command_ids)}, f)
        except Exception as e:
            App.Console.PrintWarning(f"Could not save processed IDs: {e}\n")
    
    def get_stats(self):
        with self._lock:
            uptime = (datetime.now() - self._start_time).total_seconds() if self._start_time else 0
            return {
                'monitoring_active': self._monitoring_active,
                'commands_processed': self._commands_processed,
                'errors_count': self._errors_count,
                'consecutive_errors': self._consecutive_errors,
                'last_command_time': self._last_command_time.isoformat() if self._last_command_time else None,
                'last_position': self.last_position,  # CRITICAL FIX: Include position in stats
                'uptime_seconds': uptime,
                'error_rate': self._errors_count / max(1, self._commands_processed)
            }

_state = MonitorState()
_ai_monitor_timer = None
_ai_heartbeat_timer = None
_ai_buffer_flush_timer = None
_ai_health_check_timer = None
_ai_status_timer = None
_quiet_mode = True

# Result buffer with lock
_result_buffer = []

# ============================================================
# ERROR→FIX TRACKING SYSTEM
# ============================================================
# Tracks errors so that when the next command succeeds, we can
# automatically record the error→fix pair in the learning database

class ErrorFixTracker:
    """Tracks errors and detects when AI successfully fixes them"""
    
    def __init__(self):
        self._lock = threading.RLock()
        self._pending_error = None  # Last error waiting for a fix
        self._error_timestamp = None
        self._error_timeout = 120  # Consider error stale after 2 minutes
    
    def record_error(self, command_id, command, error_message, error_type):
        """Record an error that needs AI intervention"""
        with self._lock:
            self._pending_error = {
                'command_id': command_id,
                'command': command,
                'error_message': error_message,
                'error_type': error_type,
                'timestamp': datetime.now()
            }
            self._error_timestamp = datetime.now()
            App.Console.PrintMessage(f"[LEARN] Error recorded for potential fix tracking\n")
    
    def check_for_fix(self, successful_command):
        """Check if successful command is a fix for the pending error"""
        with self._lock:
            if not self._pending_error:
                return None
            
            # Check if error is stale
            if self._error_timestamp:
                age = (datetime.now() - self._error_timestamp).total_seconds()
                if age > self._error_timeout:
                    self._pending_error = None
                    return None
            
            # Analyze if this is likely a fix for the previous error
            error_data = self._pending_error
            fix_detected = self._is_likely_fix(error_data, successful_command)
            
            if fix_detected:
                result = {
                    'original_error': error_data['error_message'],
                    'original_command': error_data['command'],
                    'error_type': error_data['error_type'],
                    'fixed_command': successful_command,
                    'solution': self._generate_solution_description(error_data, successful_command)
                }
                # Clear the pending error
                self._pending_error = None
                self._error_timestamp = None
                return result
            
            return None
    
    def _is_likely_fix(self, error_data, successful_command):
        """Determine if successful command is likely a fix for the error"""
        original = error_data['command']
        fixed = successful_command
        error_msg = error_data['error_message']
        
        # Check for similar structure but different content
        # This suggests the AI corrected the same operation
        
        # Extract key parts
        def extract_keywords(cmd):
            import re
            # Get imports, function calls, variable names
            words = set(re.findall(r'\b[a-zA-Z_][a-zA-Z0-9_]*\b', cmd))
            return words
        
        orig_keywords = extract_keywords(original)
        fix_keywords = extract_keywords(fixed)
        
        # Calculate similarity
        if not orig_keywords or not fix_keywords:
            return False
        
        overlap = len(orig_keywords & fix_keywords)
        total = len(orig_keywords | fix_keywords)
        similarity = overlap / total if total > 0 else 0
        
        # If 40-95% similar, it's likely a correction (not exact duplicate, not completely different)
        if 0.4 <= similarity <= 0.95:
            return True
        
        # Check if error message mentions something that changed
        # e.g., "has no attribute 'makePipe'" and fixed command uses different method
        if 'has no attribute' in error_msg:
            import re
            match = re.search(r"has no attribute '(\w+)'", error_msg)
            if match:
                bad_attr = match.group(1)
                # Check if bad attribute is in original but not in fixed
                if bad_attr in original and bad_attr not in fixed:
                    return True
        
        return False
    
    def _generate_solution_description(self, error_data, successful_command):
        """Generate a human-readable solution description"""
        error_msg = error_data['error_message']
        error_type = error_data['error_type']
        
        # Parse the error to generate a meaningful description
        if 'has no attribute' in error_msg:
            import re
            match = re.search(r"has no attribute '(\w+)'", error_msg)
            if match:
                bad_attr = match.group(1)
                return f"Replaced invalid attribute '{bad_attr}' with correct API method"
        
        if 'TypeError' in error_type:
            return "Fixed type mismatch by using correct parameter types"
        
        if 'NameError' in error_type:
            return "Fixed undefined variable or import"
        
        if 'SyntaxError' in error_type:
            return "Fixed syntax error in command"
        
        return f"Fixed {error_type}: Modified command to use correct FreeCAD API"
    
    def clear_pending_error(self):
        """Clear pending error (e.g., user explicitly cancelled)"""
        with self._lock:
            self._pending_error = None
            self._error_timestamp = None

_error_fix_tracker = ErrorFixTracker()
_result_buffer_lock = threading.Lock()

# Status file lock
_status_lock = threading.Lock()

# Command processing lock - prevents concurrent execution
_processing_lock = threading.Lock()

# Timer callback protection - prevents recursive timer firing
_in_timer_callback = False

# CRITICAL: Global execution flag - blocks ALL timers during command execution
_executing_command = False

# v4.0.05: press one of the progressive button. A running command
# CANNOT be interrupted -- it executes synchronously on the GUI thread,
# so the window cannot even receive the click while it runs, and
# killing it would corrupt the document. What can be done is stop
# taking new ones.
_paused = False

# v3.3.3: GUI-freeze watchdog (daemon thread + its stop signal)
_ai_watchdog_thread = None
_watchdog_stop_event = threading.Event()


def _dump_all_stacks(reason):
    """v5.0.17: write every Python thread's stack to ai_stack_dump.txt.

    The watchdog could say THAT the GUI thread froze but never WHERE, so
    three freezes in one day (10:53, 17:55, 19:54 on 2026-11-10) left
    nothing to diagnose but timestamps. faulthandler reads the frozen
    thread's frame from this one without needing the GIL holder to
    cooperate, so the frozen frame shows up even while the GUI is blocked.
    Plain file I/O only: this runs on the watchdog thread. Never raises.
    """
    try:
        import faulthandler
        path = os.path.join(AI_IO_DIR, 'ai_stack_dump.txt')
        with open(path, 'a', encoding='utf-8') as fh:
            fh.write("\n===== %s  %s =====\n"
                     % (datetime.now().isoformat(), reason))
            fh.flush()
            faulthandler.dump_traceback(file=fh, all_threads=True)
            fh.flush()
    except BaseException:
        pass

# ============================================================

# ============================================================
# v3.4.7: TRUE CONSOLE + TIMER LIVENESS
# ============================================================
# Why this exists. Every timer callback in this Bridge reported its own
# failures through App.Console.Print*. That is a module attribute, and any
# macro in the process can replace it - AI_Project_Log does, deliberately, to
# capture console output into its log. When a replacement raises, the callback
# raises out of its OWN except: handler. The heartbeat is then never written
# again, while monitoring_active - written once at start - goes on saying True
# and error_state stays null. Reproduced against the real 3.4.6 source on
# 2026-11-08, 6/6: the status file it leaves behind is indistinguishable from
# a healthy one.
#
# Two separate fixes follow from that:
#   1. The Bridge logs through the functions it captured at import, so no
#      later patch can break - or silently intercept - its own error report.
#   2. Liveness is reported by the watchdog THREAD, which keeps running when
#      the GUI event loop or a timer callback is dead. It is the only part of
#      the Bridge in a position to tell the truth about the rest of it.
_TRUE_CONSOLE = {}
for _nm in ('PrintMessage', 'PrintWarning', 'PrintError', 'PrintLog'):
    try:
        _TRUE_CONSOLE[_nm] = getattr(App.Console, _nm)
    except Exception:
        pass
try:
    del _nm
except NameError:
    pass


def _safe_console(name, text):
    """Log without trusting App.Console. Never raises."""
    fn = _TRUE_CONSOLE.get(name)
    if fn is not None:
        try:
            fn(text)
            return
        except BaseException:
            pass
    # Last resort: the real stderr, which nothing in this process rebinds.
    try:
        sys.__stderr__.write(text)
    except BaseException:
        pass


def _log_msg(text):
    _safe_console('PrintMessage', text)


def _log_warn(text):
    _safe_console('PrintWarning', text)


def _log_err(text):
    _safe_console('PrintError', text)


# Monotonic stamp of the last tick of each GUI-thread timer.
_liveness = {'monitor': None, 'status': None, 'started': None}
_liveness_lock = threading.Lock()


def _tick(which):
    """Record that a GUI-thread timer just fired. Never raises."""
    try:
        with _liveness_lock:
            _liveness[which] = time.monotonic()
    except BaseException:
        pass


def _liveness_snapshot():
    try:
        with _liveness_lock:
            return dict(_liveness)
    except BaseException:
        return {}

# PATH SECURITY VALIDATION
# ============================================================

def validate_path(path, base_dir=None):
    """
    Validate path to prevent directory traversal attacks
    
    Args:
        path: Path to validate
        base_dir: Base directory that path must be within
    
    Returns:
        Validated absolute path
    
    Raises:
        SecurityError: If path is outside allowed directory
    """
    if base_dir is None:
        base_dir = App.getUserAppDataDir()
    
    # Resolve to absolute path
    real_path = os.path.realpath(os.path.abspath(path))
    real_base = os.path.realpath(os.path.abspath(base_dir))
    
    # Check if path is within base directory
    if not real_path.startswith(real_base):
        raise SecurityError(f"Path outside allowed directory: {path}")
    
    return real_path

class SecurityError(Exception):
    """Security validation error"""
    pass

# ============================================================
# COMMAND SECURITY & VALIDATION
# ============================================================

class SecureCommandExecutor:
    """
    Hardened command executor with security validation and timeout protection
    """
    
    def __init__(self):
        self.timeout = Config.COMMAND_TIMEOUT_SEC
        self.max_command_length = Config.MAX_COMMAND_LENGTH
        self.execution_lock = threading.Lock()
        self.metrics = {
            'total_time': 0.0,
            'slowest_time': 0.0,
            'slowest_command': None
        }
    
    def validate_command(self, command):
        """
        Validate command for security issues
        
        Returns:
            (is_valid, error_message)
        """
        # Length check
        if len(command) > self.max_command_length:
            return False, f"Command too long (max {self.max_command_length} chars)"
        
        # Pattern check - only check for dangerous operations
        cmd_lower = command.lower()
        for pattern in Config.FORBIDDEN_PATTERNS:
            if pattern in cmd_lower:
                # Extra check: allow if it's within a string or comment
                if not self._is_in_string_or_comment(command, pattern):
                    return False, f"Forbidden operation: {pattern}"
        
        # AST validation - relaxed for FreeCAD operations
        BLOCKED_MODULES = {'os', 'sys', 'subprocess', 'socket', 'urllib', 'shutil'}
        try:
            tree = ast.parse(command)
            for node in ast.walk(tree):
                # Check 'import X' statements
                if isinstance(node, ast.Import):
                    for alias in node.names:
                        module_root = alias.name.split('.')[0]
                        if module_root in BLOCKED_MODULES:
                            return False, f"Module not allowed: {alias.name}"
                # Check 'from X import Y' statements
                elif isinstance(node, ast.ImportFrom):
                    if node.module:
                        module_root = node.module.split('.')[0]
                        if module_root in BLOCKED_MODULES:
                            return False, f"Module not allowed: {node.module}"
                # Check importlib.import_module('blocked') calls
                elif isinstance(node, ast.Call):
                    func = node.func
                    # Match: importlib.import_module('sys') or similar
                    if (isinstance(func, ast.Attribute) and
                        func.attr == 'import_module' and
                        node.args):
                        arg = node.args[0]
                        if isinstance(arg, ast.Constant) and isinstance(arg.value, str):
                            mod_root = arg.value.split('.')[0]
                            if mod_root in BLOCKED_MODULES:
                                return False, f"Module not allowed via import_module: {arg.value}"

        except SyntaxError as e:
            # Syntax errors will be caught during execution
            pass
        
        return True, None
    
    def _is_in_string_or_comment(self, command, pattern):
        """Check if pattern appears only in strings or comments"""
        # Simple heuristic - if pattern is in quotes, it's probably in a string
        import re
        # Remove strings first
        no_strings = re.sub(r'["\'].*?["\']', '', command)
        # Remove comments
        no_comments = re.sub(r'#.*', '', no_strings)
        return pattern not in no_comments.lower()
    
    def execute_with_timeout(self, command, command_id=None):
        """
        Execute command with timeout protection and sandboxing
        
        CRITICAL FIX: Execute directly in main thread to prevent Qt event loop issues
        
        Returns:
            Result dictionary with success status and output
        """
        # Validate first
        is_valid, error = self.validate_command(command)
        if not is_valid:
            return {
                'command_id': command_id,
                'command': command,
                'timestamp': datetime.now().isoformat(),
                'success': False,
                'error': f"Security validation failed: {error}",
                'output': None,
                'security_blocked': True
            }
        
        # CRITICAL FIX: Execute directly without threading to prevent Qt event issues
        # The threading was causing Qt event loops to trigger timers recursively
        with self.execution_lock:
            result = self._execute_command(command, command_id)
            return result
    
    def _execute_command(self, command, command_id):
        """Internal execution with output capture and sandboxing"""
        from io import StringIO
        
        result = {
            'command_id': command_id,
            'command': command,
            'timestamp': datetime.now().isoformat(),
            'success': False,
            'output': None,
            'error': None
        }
        
        # Capture output
        old_stdout = sys.stdout
        old_stderr = sys.stderr
        capture_stdout = StringIO()
        capture_stderr = StringIO()
        
        try:
            sys.stdout = capture_stdout
            sys.stderr = capture_stderr
            
            # Restricted globals - with controlled import access.
            #
            # v5.0.18: a DENY-list of builtins, not a 30-name allow-list.
            # Whatever a command's frame carries as __builtins__ is also what
            # FreeCAD runs a lazily-loaded GUI module's start-up code under,
            # because that load happens INSIDE the command (the first
            # Part::Feature pulls in PartGui). Under the allow-list that
            # start-up code failed inside C++, which called abort(): FreeCAD's
            # SIGABRT handler turned the first one into "InterruptedError:
            # Break signal occurred" and the next killed the process
            # (0xC0000409). A direct `import PartGui` under the same builtins
            # hung the GUI thread at 0% CPU instead. Reproduced in fresh
            # FreeCAD processes with no Bridge loaded, 2026-11-10: allow-list
            # fails, deny-list passes, the stdout swap and eval->exec do not
            # matter. The dangerous names stay out, and the command validator
            # still blocks them as text, so this is the same boundary -- it
            # just stops breaking FreeCAD's own import machinery.
            exec_globals = {
                'App': App,
                'Gui': Gui,
                'FreeCAD': App,
                'FreeCADGui': Gui,
                '__builtins__': _sandbox_builtins(),
            }
            
            # Import allowed modules safely
            try:
                import Part
                exec_globals['Part'] = Part
            except ImportError:
                pass
            
            try:
                import Draft
                exec_globals['Draft'] = Draft
            except ImportError:
                pass
            
            try:
                import Sketcher
                exec_globals['Sketcher'] = Sketcher
            except ImportError:
                pass
            
            try:
                import Mesh
                exec_globals['Mesh'] = Mesh
            except ImportError:
                pass
            
            try:
                import math
                exec_globals['math'] = math
            except ImportError:
                pass

            # v5.0.17: the Bridge's own agent API -- parametric memory,
            # inventory, capture and outsource as named verbs. The same
            # object sits on App.AIBridge for run_macro files.
            exec_globals['AIBridge'] = getattr(App, 'AIBridge', None)

            # Clear console monitor before execution
            _console_monitor.clear()
            
            # Execute command
            try:
                exec_result = eval(command, exec_globals)
                stdout_content = capture_stdout.getvalue()
                stderr_content = capture_stderr.getvalue()
                
                result['success'] = True
                result['output'] = {
                    'result': str(exec_result) if exec_result is not None else None,
                    'stdout': stdout_content if stdout_content else None,
                    'stderr': stderr_content if stderr_content else None
                }
            except SyntaxError:
                # Try exec instead of eval for statements
                exec(command, exec_globals)
                stdout_content = capture_stdout.getvalue()
                stderr_content = capture_stderr.getvalue()
                
                result['success'] = True
                result['output'] = {
                    'result': None,
                    'stdout': stdout_content if stdout_content else None,
                    'stderr': stderr_content if stderr_content else None
                }
            
            # CRITICAL: Capture FreeCAD console state after execution
            console_state = _console_monitor.capture_console_state()
            result['console_state'] = console_state
            
            # Check for FreeCAD-specific warnings/errors
            if console_state.get('has_warnings') or console_state.get('has_errors'):
                result['freecad_warnings'] = console_state.get('warnings', [])
                result['freecad_errors'] = console_state.get('errors', [])
                result['needs_correction'] = True
                
        except Exception as e:
            result['error'] = f"{type(e).__name__}: {str(e)}"
            # v5.0.17: keep the traceback HERE, inside the except. The
            # error log called traceback.format_exc() long after this block
            # had closed, so every entry read "Traceback: NoneType: None" --
            # including all three "Break signal occurred" failures, whose
            # one useful fact is which line of the command raised.
            result['traceback'] = traceback.format_exc()
            stderr_content = capture_stderr.getvalue()
            if stderr_content:
                result['error'] += f"\n{stderr_content}"

        finally:
            sys.stdout = old_stdout
            sys.stderr = old_stderr

        return result

SANDBOX_DENIED_BUILTINS = frozenset((
    # file and console I/O
    'open', 'input',
    # running code that the validator never saw
    'eval', 'exec', 'compile', 'breakpoint',
    # reaching or rewriting namespaces and objects
    'globals', 'locals', 'vars', 'setattr', 'delattr',
    # interactive helpers that block or exit the host
    'help', 'exit', 'quit',
    # raw memory views
    'memoryview',
))


def _sandbox_builtins():
    """Python's own builtins minus SANDBOX_DENIED_BUILTINS (v5.0.18).

    A fresh dict per command, so nothing a command does to it can leak into
    the next one. __import__ stays, as it always has: imports are policed by
    the command validator, and without it no module could load at all.
    """
    import builtins as _bi
    safe = dict((k, v) for k, v in vars(_bi).items()
                if k not in SANDBOX_DENIED_BUILTINS)
    safe['__name__'] = '__main__'
    safe['__doc__'] = None
    return safe


# Global executor instance
_executor = SecureCommandExecutor()

# ============================================================
# FREECAD CONSOLE MONITORING - Report View Capture
# ============================================================

class FreeCADConsoleMonitor:
    """Monitor FreeCAD console for warnings and errors during command execution"""
    
    def __init__(self):
        self.messages = []
        self.warnings = []
        self.errors = []
        
    def clear(self):
        """Clear captured messages"""
        self.messages = []
        self.warnings = []
        self.errors = []
    
    def capture_console_state(self):
        """Capture current console state from FreeCAD"""
        try:
            # Capture from active document
            if App.ActiveDocument:
                # Check for document errors
                for obj in App.ActiveDocument.Objects:
                    if hasattr(obj, 'State'):
                        if 'Invalid' in str(obj.State) or 'Error' in str(obj.State):
                            self.errors.append(f"Object {obj.Label}: {obj.State}")
                    
                    # Check Sketcher constraints
                    if obj.isDerivedFrom('Sketcher::SketchObject'):
                        if hasattr(obj, 'Conflicts'):
                            conflicts = obj.Conflicts
                            if conflicts:
                                self.warnings.append(f"Sketch {obj.Label}: Over-constrained - conflicts: {conflicts}")
                        
                        dof = obj.Shape.Faces[0].Surface.Continuity if hasattr(obj, 'Shape') and obj.Shape.Faces else None
                        if hasattr(obj, 'getDegreeOfFreedom'):
                            try:
                                dof_val = obj.getDegreeOfFreedom()
                                if dof_val < 0:
                                    self.warnings.append(f"Sketch {obj.Label}: Over-constrained (DOF={dof_val})")
                                elif dof_val > 0:
                                    self.warnings.append(f"Sketch {obj.Label}: Under-constrained (DOF={dof_val})")
                            except:
                                pass
            
            return {
                'has_errors': len(self.errors) > 0,
                'has_warnings': len(self.warnings) > 0,
                'errors': self.errors[:],
                'warnings': self.warnings[:]
            }
            
        except Exception as e:
            return {'has_errors': False, 'has_warnings': False, 'errors': [], 'warnings': []}

# Global console monitor
_console_monitor = FreeCADConsoleMonitor()

# ============================================================
# ERROR PATTERN DETECTION & AUTO-CORRECTION
# ============================================================

class AutoCorrectionSystem:
    """Intelligent error detection and automatic correction"""
    
    def __init__(self, learning_system):
        self.learning_system = learning_system
        self.correction_patterns = self._initialize_patterns()
    
    def _initialize_patterns(self):
        """Initialize known error patterns and corrections"""
        return {
            'over_constrained_sketch': {
                'detect': lambda msg: 'over-constrained' in msg.lower() or 'conflicts' in msg.lower(),
                'analyze': self._analyze_overconstrained,
                'fix': self._fix_overconstrained
            },
            'under_constrained_sketch': {
                'detect': lambda msg: 'under-constrained' in msg.lower() or 'dof' in msg.lower(),
                'analyze': self._analyze_underconstrained,
                'fix': self._fix_underconstrained
            },
            'recompute_failed': {
                'detect': lambda msg: 'recompute' in msg.lower() and 'fail' in msg.lower(),
                'analyze': self._analyze_recompute_failure,
                'fix': self._fix_recompute_failure
            },
            'geometry_error': {
                'detect': lambda msg: 'geometry' in msg.lower() and ('invalid' in msg.lower() or 'error' in msg.lower()),
                'analyze': self._analyze_geometry_error,
                'fix': self._fix_geometry_error
            }
        }
    
    def detect_and_correct(self, command, console_state, command_id):
        """Detect errors and generate corrected command"""
        corrections = []
        
        # Check warnings
        for warning in console_state.get('warnings', []):
            for pattern_name, pattern in self.correction_patterns.items():
                if pattern['detect'](warning):
                    analysis = pattern['analyze'](command, warning, console_state)
                    if analysis:
                        fix = pattern['fix'](command, analysis)
                        if fix:
                            corrections.append({
                                'type': pattern_name,
                                'warning': warning,
                                'analysis': analysis,
                                'corrected_command': fix,
                                'confidence': analysis.get('confidence', 0.8)
                            })
        
        # Check errors
        for error in console_state.get('errors', []):
            for pattern_name, pattern in self.correction_patterns.items():
                if pattern['detect'](error):
                    analysis = pattern['analyze'](command, error, console_state)
                    if analysis:
                        fix = pattern['fix'](command, analysis)
                        if fix:
                            corrections.append({
                                'type': pattern_name,
                                'error': error,
                                'analysis': analysis,
                                'corrected_command': fix,
                                'confidence': analysis.get('confidence', 0.9)
                            })
        
        return corrections
    
    def _analyze_overconstrained(self, command, message, console_state):
        """Analyze over-constrained sketch"""
        # Extract conflict information
        import re
        conflicts = re.findall(r'\d+', message)
        
        # Count constraint types in command
        constraint_counts = {
            'Coincident': command.count('Coincident'),
            'Symmetric': command.count('Symmetric'),
            'Distance': command.count('Distance'),
            'DistanceX': command.count('DistanceX'),
            'DistanceY': command.count('DistanceY'),
            'Horizontal': command.count('Horizontal'),
            'Vertical': command.count('Vertical')
        }
        
        return {
            'conflicts': conflicts,
            'constraint_counts': constraint_counts,
            'redundant_likely': ['Symmetric', 'Coincident'],  # Common redundant constraints
            'confidence': 0.85
        }
    
    def _fix_overconstrained(self, command, analysis):
        """Generate fix for over-constrained sketch"""
        # Strategy: Remove symmetry constraints (common cause)
        # Keep geometric (H/V) and dimensional constraints
        
        lines = command.split('\n')
        fixed_lines = []
        symmetric_removed = 0
        
        for line in lines:
            # Remove Symmetric constraints (usually redundant with other constraints)
            if 'Symmetric' in line and symmetric_removed < 2:
                fixed_lines.append('# REMOVED (redundant): ' + line)
                symmetric_removed += 1
            else:
                fixed_lines.append(line)
        
        if symmetric_removed > 0:
            return '\n'.join(fixed_lines)
        
        # Alternative: Remove some coincident constraints
        fixed_lines = []
        coincident_removed = 0
        for line in lines:
            if 'Coincident' in line and coincident_removed < 1:
                fixed_lines.append('# REMOVED (redundant): ' + line)
                coincident_removed += 1
            else:
                fixed_lines.append(line)
        
        return '\n'.join(fixed_lines) if coincident_removed > 0 else None
    
    def _analyze_underconstrained(self, command, message, console_state):
        """Analyze under-constrained sketch"""
        return {
            'message': message,
            'suggestion': 'Add more constraints or fix to origin',
            'confidence': 0.7
        }
    
    def _fix_underconstrained(self, command, analysis):
        """Generate fix for under-constrained sketch"""
        # Add fix constraint to origin (common solution)
        if 'addConstraint' in command:
            return command + "\n# Fix sketch to origin\nsketch.addConstraint(Sketcher.Constraint('Coincident', 0, 1, -1, 1))"
        return None
    
    def _analyze_recompute_failure(self, command, message, console_state):
        """Analyze recompute failure"""
        return {'message': message, 'confidence': 0.6}
    
    def _fix_recompute_failure(self, command, analysis):
        """Generate fix for recompute failure"""
        # Add explicit recompute with error handling
        if 'recompute()' not in command:
            return command + "\ndoc.recompute()\nGui.updateGui()"
        return None
    
    def _analyze_geometry_error(self, command, message, console_state):
        """Analyze geometry error"""
        return {'message': message, 'confidence': 0.5}
    
    def _fix_geometry_error(self, command, analysis):
        """Generate fix for geometry error"""
        return None  # Too complex for automatic fixing

# Global auto-correction system (initialized after learning system)
_auto_correction = None

# ============================================================
# AI LEARNING SYSTEM - Thread-Safe
# ============================================================

class AILearningSystem:
    """
    Thread-safe learning system with backup and validation
    """
    
    def __init__(self, db_path=LEARNING_DB_FILE):
        self.db_path = db_path
        self.db_lock = threading.RLock()
        self.db = self._load_database()
        self._build_search_index()
    
    def _load_database(self):
        """Load database with validation and recovery"""
        paths_to_try = [
            self.db_path,
            f"{self.db_path}.backup",
            f"{self.db_path}.backup.1",
            f"{self.db_path}.backup.2"
        ]
        
        for path in paths_to_try:
            if not os.path.exists(path):
                continue
            
            try:
                with open(path, 'r', encoding='utf-8') as f:
                    data = json.load(f)
                
                # Validate schema
                if self._validate_schema(data):
                    if path != self.db_path:
                        App.Console.PrintWarning(f"[DB] Loaded learning DB from backup: {path}\n")
                    return data
                else:
                    App.Console.PrintWarning(f"Invalid schema in {path}\n")
            
            except json.JSONDecodeError as e:
                App.Console.PrintWarning(f"Corrupted JSON in {path}: {e}\n")
            except Exception as e:
                App.Console.PrintWarning(f"Cannot load {path}: {e}\n")
        
        # All attempts failed - create new database
        App.Console.PrintMessage("[DB] Creating new learning database\n")
        return self._initialize_empty_database()
    
    def _validate_schema(self, data):
        """Validate database structure"""
        required_keys = {'metadata', 'successful_patterns', 
                        'error_resolutions', 'command_templates', 
                        'common_mistakes'}
        return isinstance(data, dict) and all(key in data for key in required_keys)
    
    def _initialize_empty_database(self):
        """Initialize new database structure"""
        return {
            "metadata": {
                "created": datetime.now().isoformat(),
                "last_updated": datetime.now().isoformat(),
                "version": "1.0",
                "total_patterns": 0,
                "total_errors_resolved": 0
            },
            "successful_patterns": [],
            "error_resolutions": [],
            "command_templates": {},
            "common_mistakes": []
        }
    
    def _save_database(self):
        """Thread-safe save with backup"""
        with self.db_lock:
            try:
                # Ensure directory exists
                os.makedirs(os.path.dirname(self.db_path), exist_ok=True)
                
                # Create backup of existing database
                if os.path.exists(self.db_path):
                    # Rotate backups
                    for i in range(Config.MAX_DATABASE_BACKUPS - 1, 0, -1):
                        old_backup = f"{self.db_path}.backup.{i-1}" if i > 1 else f"{self.db_path}.backup"
                        new_backup = f"{self.db_path}.backup.{i}"
                        if os.path.exists(old_backup):
                            shutil.copy2(old_backup, new_backup)
                    
                    # Create new backup
                    shutil.copy2(self.db_path, f"{self.db_path}.backup")
                
                # Prune database to maintain size limits
                self._prune_database()
                
                # Update metadata
                self.db["metadata"]["last_updated"] = datetime.now().isoformat()
                self.db["metadata"]["total_patterns"] = len(self.db["successful_patterns"])
                self.db["metadata"]["total_errors_resolved"] = len(self.db["error_resolutions"])
                
                # Write to temp file first
                temp_path = f"{self.db_path}.tmp"
                with open(temp_path, 'w', encoding='utf-8') as f:
                    json.dump(self.db, f, indent=2, ensure_ascii=False)
                
                # Verify temp file is valid JSON
                with open(temp_path, 'r') as f:
                    json.load(f)
                
                # Atomic replace
                os.replace(temp_path, self.db_path)
                
                # Rebuild search index after save
                self._build_search_index()
                
                return True
                
            except Exception as e:
                App.Console.PrintError(f"Learning database save failed: {e}\n")
                # Try to restore from backup
                backup_path = f"{self.db_path}.backup"
                if os.path.exists(backup_path):
                    try:
                        shutil.copy2(backup_path, self.db_path)
                        App.Console.PrintMessage("Restored database from backup\n")
                    except Exception as restore_error:
                        App.Console.PrintError(f"Could not restore from backup: {restore_error}\n")
                        pass
                return False
    
    def _prune_database(self):
        """Keep database at manageable size"""
        # Prune successful patterns - keep most used
        if len(self.db["successful_patterns"]) > Config.MAX_SUCCESSFUL_PATTERNS:
            sorted_patterns = sorted(
                self.db["successful_patterns"],
                key=lambda x: x.get("success_count", 0),
                reverse=True
            )
            self.db["successful_patterns"] = sorted_patterns[:Config.MAX_SUCCESSFUL_PATTERNS]
        
        # Prune error resolutions - keep most recent
        if len(self.db["error_resolutions"]) > Config.MAX_ERROR_RESOLUTIONS:
            sorted_errors = sorted(
                self.db["error_resolutions"],
                key=lambda x: x.get("timestamp", ""),
                reverse=True
            )
            self.db["error_resolutions"] = sorted_errors[:Config.MAX_ERROR_RESOLUTIONS]
        
        # Prune common mistakes - keep most recent
        if len(self.db["common_mistakes"]) > Config.MAX_COMMON_MISTAKES:
            sorted_mistakes = sorted(
                self.db["common_mistakes"],
                key=lambda x: x.get("timestamp", ""),
                reverse=True
            )
            self.db["common_mistakes"] = sorted_mistakes[:Config.MAX_COMMON_MISTAKES]
    
    def _build_search_index(self):
        """Build search index for fast lookups"""
        self._error_index = {}
        for resolution in self.db["error_resolutions"]:
            error_text = resolution["original_error"].lower()
            words = error_text.split()
            for word in words:
                if len(word) > 3:  # Skip short words
                    if word not in self._error_index:
                        self._error_index[word] = []
                    self._error_index[word].append(resolution)
    
    def normalize_command(self, command):
        """Normalize command for comparison"""
        # Remove whitespace variations
        normalized = re.sub(r'\s+', ' ', command.strip())
        # Remove comments
        normalized = re.sub(r'#.*$', '', normalized, flags=re.MULTILINE)
        return normalized
    
    def record_success(self, command, description, category="general",
                       source_agent=None, verified=None):
        """Thread-safe record success with fuzzy duplicate detection.

        v3.4.0 PROVENANCE (Phase 7): every pattern is tagged with the agent
        that produced it. Output from a local model is stored UNVERIFIED and
        excluded from the context fed to future agents until a human promotes
        it. record_success() fires on anything that does not raise - and a
        small model produces plenty of code that runs fine while being wrong.
        Left ungated, that quietly degrades the knowledge base every agent
        reads.
        """
        source_agent = source_agent or "unknown"
        if verified is None:
            verified = (source_agent != Config.OLLAMA_AGENT_ID)

        with self.db_lock:
            normalized_cmd = self.normalize_command(command)
            
            # Check for duplicates
            for existing in self.db["successful_patterns"]:
                if self.normalize_command(existing["command"]) == normalized_cmd:
                    existing["success_count"] += 1
                    existing["last_used"] = datetime.now().isoformat()
                    existing["command"] = command  # Update to newest version
                    # v3.4.0: never DOWNGRADE an already-verified pattern, but do
                    # record that an unverified agent also produced it
                    existing.setdefault("source_agent", source_agent)
                    if verified:
                        existing["verified"] = True
                    else:
                        existing.setdefault("verified", False)
                    # LEARNING: auto-promote a proven command to a reusable template (>=3 uses)
                    # v3.4.0: VERIFIED patterns only - an unreviewed local-model command
                    # must not become a canonical template just by repeating.
                    try:
                        if (int(existing.get("success_count", 0)) >= 3
                                and existing.get("verified", True)):
                            _tname = str(existing.get("category", "general")) + "_" + str(abs(hash(normalized_cmd)) % 100000)
                            if _tname not in self.db["command_templates"]:
                                self.db["command_templates"][_tname] = {
                                    "code": command,
                                    "parameters": [],
                                    "description": existing.get("description", "auto-promoted from repeated success"),
                                    "added": datetime.now().isoformat(),
                                    "usage_count": int(existing.get("success_count", 0)),
                                }
                    except Exception:
                        pass
                    self._save_database()
                    return
            
            # Add new pattern
            pattern = {
                "timestamp": datetime.now().isoformat(),
                "command": command,
                "description": description,
                "category": category,
                "success_count": 1,
                "source_agent": source_agent,   # v3.4.0 provenance
                "verified": bool(verified)
            }
            self.db["successful_patterns"].append(pattern)
            self._save_database()

    def promote_pattern(self, command):
        """v3.4.0 Phase 7: human-in-the-loop promotion to verified.

        Called from the Ollama panel after you have actually looked at the
        geometry. Returns True if a matching pattern was found.
        """
        with self.db_lock:
            normalized = self.normalize_command(command)
            for pattern in self.db.get("successful_patterns", []):
                if self.normalize_command(pattern.get("command", "")) == normalized:
                    pattern["verified"] = True
                    pattern["verified_at"] = datetime.now().isoformat()
                    self._save_database()
                    return True
        return False

    def migrate_provenance(self):
        """One-time backfill: pre-v3.4.0 entries predate Ollama, so they came
        from a frontier agent and are treated as verified."""
        changed = 0
        with self.db_lock:
            for pattern in self.db.get("successful_patterns", []):
                if "source_agent" not in pattern:
                    pattern["source_agent"] = "legacy"
                    pattern["verified"] = True
                    changed += 1
            if changed:
                self._save_database()
        if changed:
            App.Console.PrintMessage(
                f"[PROVENANCE] Backfilled {changed} legacy patterns as verified\n")
        return changed

    def get_provenance_stats(self):
        """Counts by source agent and verification state."""
        stats = {'total': 0, 'verified': 0, 'unverified': 0, 'by_agent': {}}
        for pattern in self.db.get("successful_patterns", []):
            stats['total'] += 1
            if pattern.get('verified', True):
                stats['verified'] += 1
            else:
                stats['unverified'] += 1
            agent = pattern.get('source_agent', 'unknown')
            stats['by_agent'][agent] = stats['by_agent'].get(agent, 0) + 1
        return stats

    
    def record_error_resolution(self, original_error, original_command, fixed_command, solution_description):
        """Thread-safe record error resolution"""
        with self.db_lock:
            # Check for duplicates
            for existing in self.db["error_resolutions"]:
                if existing["original_error"] == original_error:
                    existing["occurrence_count"] += 1
                    existing["last_occurred"] = datetime.now().isoformat()
                    # LEARNING: promote a recurring error to a common mistake
                    try:
                        if int(existing.get("occurrence_count", 0)) >= 2:
                            _key = str(original_error)[:150]
                            if not any(m.get("mistake") == _key for m in self.db["common_mistakes"]):
                                self.db["common_mistakes"].append({
                                    "timestamp": datetime.now().isoformat(),
                                    "mistake": _key,
                                    "why_wrong": existing.get("solution", ""),
                                    "correct_approach": str(existing.get("fixed_command", ""))[:400],
                                    "occurrence_count": int(existing.get("occurrence_count", 0)),
                                })
                    except Exception:
                        pass
                    self._save_database()
                    return
            
            # Add new resolution
            resolution = {
                "timestamp": datetime.now().isoformat(),
                "original_error": original_error,
                "original_command": original_command,
                "fixed_command": fixed_command,
                "solution": solution_description,
                "occurrence_count": 1
            }
            self.db["error_resolutions"].append(resolution)
            self._save_database()
    
    def record_common_mistake(self, mistake_description, why_wrong, correct_approach):
        """Thread-safe record common mistake"""
        with self.db_lock:
            mistake = {
                "timestamp": datetime.now().isoformat(),
                "mistake": mistake_description,
                "why_wrong": why_wrong,
                "correct_approach": correct_approach
            }
            self.db["common_mistakes"].append(mistake)
            self._save_database()
    
    def add_command_template(self, template_name, template_code, parameters, description):
        """Thread-safe add command template"""
        with self.db_lock:
            self.db["command_templates"][template_name] = {
                "code": template_code,
                "parameters": parameters,
                "description": description,
                "added": datetime.now().isoformat(),
                "usage_count": 0
            }
            self._save_database()
    
    def get_template(self, template_name):
        """Thread-safe get template"""
        with self.db_lock:
            template = self.db["command_templates"].get(template_name)
            if template:
                template["usage_count"] += 1
                self._save_database()
            return template
    
    def search_solutions(self, error_text):
        """Fast indexed search for solutions"""
        with self.db_lock:
            error_lower = error_text.lower()
            words = error_lower.split()
            
            # Get candidate resolutions from index
            candidates = set()
            for word in words:
                if word in self._error_index:
                    candidates.update(tuple(r.items()) for r in self._error_index[word])
            
            # Convert back to dicts and rank by relevance
            matches = []
            for candidate_tuple in candidates:
                resolution = dict(candidate_tuple)
                if error_lower in resolution["original_error"].lower():
                    matches.append(resolution)
            
            return matches
    
    def get_stats(self):
        """Thread-safe get statistics"""
        with self.db_lock:
            return {
                "total_patterns": len(self.db["successful_patterns"]),
                "total_resolutions": len(self.db["error_resolutions"]),
                "total_templates": len(self.db["command_templates"]),
                "total_mistakes": len(self.db["common_mistakes"]),
                "last_updated": self.db["metadata"]["last_updated"]
            }

# Initialize global learning system
_learning_system = AILearningSystem()

# v3.4.0 Phase 7: one-time backfill of provenance fields on pre-3.4.0 entries.
# Anything already in the database predates Ollama, so it came from a frontier
# agent and is treated as verified.
try:
    _learning_system.migrate_provenance()
except Exception as _e:
    App.Console.PrintWarning(f"[PROVENANCE] Migration skipped: {_e}\n")

# Initialize auto-correction system
_auto_correction = AutoCorrectionSystem(_learning_system)

# ============================================================
# ERROR LOGGING & MONITORING
# ============================================================

def log_error_with_context(error, command_id, command_text, additional_context=None):
    """Log error with full context for debugging"""
    try:
        with open(ERROR_LOG_FILE, 'a', encoding='utf-8') as f:
            f.write(f"\n{'='*70}\n")
            f.write(f"Error occurred at: {datetime.now().isoformat()}\n")
            f.write(f"Command ID: {command_id}\n")
            f.write(f"Command: {command_text}\n")
            f.write(f"Error: {str(error)}\n")
            # v5.0.17: a traceback captured where the exception was caught
            # wins; format_exc() here is only right when called inside an
            # except, which most callers are not.
            tb = (additional_context or {}).get('traceback') or \
                traceback.format_exc()
            f.write(f"Traceback:\n{tb}\n")
            f.write(f"System state:\n")
            stats = _state.get_stats()
            for key, value in stats.items():
                f.write(f"  {key}: {value}\n")
            if additional_context:
                f.write(f"Additional context:\n")
                for key, value in additional_context.items():
                    f.write(f"  {key}: {value}\n")
            f.write(f"{'='*70}\n")
    except Exception as e:
        App.Console.PrintError(f"Cannot write error log: {e}\n")

# ============================================================
# FILE OPERATIONS - With Rotation
# ============================================================

def rotate_file_if_needed(filepath, max_size=Config.MAX_OUTPUT_FILE_SIZE):
    """Rotate file if it exceeds size limit"""
    if not os.path.exists(filepath):
        return
    
    size = os.path.getsize(filepath)
    if size > max_size:
        # Create archive
        timestamp = datetime.now().strftime('%Y%m%d_%H%M%S')
        archive = f"{filepath}.{timestamp}"
        os.rename(filepath, archive)
        
        # Clean old archives
        pattern = f"{filepath}.*"
        archives = sorted(glob.glob(pattern))
        if len(archives) > Config.MAX_ARCHIVE_FILES:
            for old_file in archives[:-Config.MAX_ARCHIVE_FILES]:
                try:
                    os.remove(old_file)
                    App.Console.PrintMessage(f"Deleted old archive: {os.path.basename(old_file)}\n")
                except Exception as e:
                    App.Console.PrintWarning(f"Could not delete archive {old_file}: {e}\n")
                    pass

def write_output(output_file, data_type, content, metadata=None):
    """Write structured output to AI agent output file"""
    entry = {
        'timestamp': datetime.now().isoformat(),
        'type': data_type,
        'content': content,
        'metadata': metadata or {}
    }
    
    try:
        # Check if rotation needed
        rotate_file_if_needed(output_file)
        
        with open(output_file, 'a', encoding='utf-8') as f:
            f.write(json.dumps(_conform(entry), ensure_ascii=False) + '\n')
        return True
    except Exception as e:
        App.Console.PrintError(f"Error writing to {output_file}: {str(e)}\n")
        return False

def generate_fix_suggestion(result, db_suggestions, tech_refs):
    """Generate human-readable fix suggestion for AI agent"""
    error_msg = result.get('error', '')
    error_type = error_msg.split(':')[0] if ':' in error_msg else 'Error'
    
    suggestions = []
    
    # Type-specific suggestions
    if 'SyntaxError' in error_type:
        suggestions.append("Check Python syntax - likely issue with quotes, indentation, or line continuation")
    elif 'NameError' in error_type:
        suggestions.append("Variable or function not defined - check imports and spelling")
    elif 'AttributeError' in error_type:
        suggestions.append("Object doesn't have requested attribute - check FreeCAD API documentation")
    elif 'TypeError' in error_type:
        suggestions.append("Type mismatch - check function arguments and their types")
    elif 'IndexError' in error_type:
        suggestions.append("Index out of range - check list/array bounds")
    elif 'KeyError' in error_type:
        suggestions.append("Dictionary key not found - verify key exists before accessing")
    
    # Add database suggestions
    if db_suggestions:
        top_suggestion = db_suggestions[0]
        suggestions.append(f"Similar error resolved before: {top_suggestion.get('solution', 'See learning database')}")
    
    # Add doc references
    if tech_refs:
        top_ref = tech_refs[0]
        suggestions.append(f"See {top_ref.get('file', 'technical documentation')} for relevant guidance")
    
    return " | ".join(suggestions) if suggestions else "Review error message and command syntax"

def write_comprehensive_report_for_ai(result, command, command_id, agent_id=None):
    """Write comprehensive error/result report for AI agent with learning database context"""
    global _learning_system, _tech_reviewer

    # For successful commands, ALWAYS write result (even if output is None)
    if result.get('success'):
        output_data = result.get('output', {})
        report = {
            "type": "command_result",
            "command_id": command_id,
            "timestamp": datetime.now().isoformat(),
            "success": True,
            "result": output_data.get('result') if output_data else None,
            "stdout": output_data.get('stdout') if output_data else None,
            "command_preview": command[:200] + "..." if len(command) > 200 else command
        }
        # Include Report View and notifications if captured
        if result.get('report_view', {}).get('message_count', 0) > 0:
            report["report_view"] = result['report_view']
        if result.get('notifications', {}).get('notification_count', 0) > 0:
            report["notifications"] = result['notifications']
        if agent_id:
            report["agent_id"] = agent_id
        write_output(AI_OUTPUT_FILE, "command_result", report)
        return
    
    # For errors, write comprehensive report
    if not result.get('success'):
        error_text = result.get('error', 'Unknown error')
        
        # Search learning database for similar errors
        suggestions = []
        if _learning_system:
            try:
                suggestions = _learning_system.search_solutions(error_text)
            except Exception as e:
                App.Console.PrintWarning(f"Learning database search failed: {e}\n")
        
        # Search technical documentation
        tech_refs = []
        if _tech_reviewer:
            try:
                tech_refs = _tech_reviewer.search_for_error(error_text)
            except Exception as e:
                App.Console.PrintWarning(f"Technical documentation search failed: {e}\n")
        
        # Build comprehensive error report
        error_report = {
            "type": "error_report_requires_ai_intervention",
            "command_id": command_id,
            "agent_id": agent_id,
            "timestamp": datetime.now().isoformat(),
            "original_command": command,
            "error_details": {
                "error_type": error_text.split(':')[0] if ':' in error_text else 'Error',
                "error_message": error_text,
                # v5.0.17: the line that raised, so the agent does not have
                # to guess which statement of a long command failed.
                "traceback": result.get('traceback'),
                "console_state": result.get('console_state', {}),
                "console_warnings": result.get('freecad_warnings', []),
                "console_errors": result.get('freecad_errors', []),
                "report_view": result.get('report_view', {}),
                "notifications": result.get('notifications', {})
            },
            "auto_correction_attempted": result.get('auto_correction_attempted', False),
            "auto_correction_failed": result.get('auto_correction_failed', False),
            "auto_correction_unavailable": result.get('auto_correction_unavailable', False),
            "auto_corrected": result.get('auto_corrected', False),
            "corrected_command": result.get('corrected_command'),
            "learning_database_suggestions": [
                {
                    "similar_error": s.get('original_error', '')[:200],
                    "previous_solution": s.get('solution', ''),
                    "fixed_command": s.get('fixed_command', '')[:500],
                    "confidence": s.get('occurrence_count', 1) / 10.0  # Normalize to 0-1
                }
                for s in suggestions[:3]  # Top 3 suggestions
            ],
            "technical_documentation_references": [
                {
                    "file": ref.get('file', ''),
                    "relevance": ref.get('relevance', 'unknown'),
                    "matches": ref.get('matches', [])[:3]  # Top 3 matches per file
                }
                for ref in tech_refs[:3]  # Top 3 files
            ],
            "suggested_fix_approach": generate_fix_suggestion(result, suggestions, tech_refs),
            "ai_action_required": True
        }
        
        # Write to output file
        write_output(AI_OUTPUT_FILE, "error_report", error_report)
        
        # Log that report was written
        App.Console.PrintMessage(f"[AI-REPORT] Comprehensive error report written for AI agent\n")
        if suggestions:
            App.Console.PrintMessage(f"[AI-REPORT] Included {len(suggestions)} similar error resolutions\n")
        if tech_refs:
            App.Console.PrintMessage(f"[AI-REPORT] Included {len(tech_refs)} technical documentation references\n")

# ============================================================
# BUFFER MANAGEMENT - Actually Flushing Now!
# ============================================================

def flush_result_buffer():
    """Flush buffered results to disk - NOW ACTUALLY CALLED!"""
    global _result_buffer
    
    with _result_buffer_lock:
        if not _result_buffer:
            return
        
        try:
            rotate_file_if_needed(AI_OUTPUT_FILE)
            
            with open(AI_OUTPUT_FILE, 'a', encoding='utf-8') as f:
                for entry in _result_buffer:
                    f.write(json.dumps(_conform(entry), ensure_ascii=False) + '\n')
            
            count = len(_result_buffer)
            _result_buffer.clear()
            
            # Only log if we flushed a significant amount
            if count > 10:
                App.Console.PrintMessage(f"[FLUSH] Flushed {count} results to disk\n")
                
        except IOError as e:
            App.Console.PrintError(f"Cannot write results: {e}\n")
            # Keep buffer for retry
        except Exception as e:
            App.Console.PrintError(f"Flush error: {e}\n")
            _result_buffer.clear()  # Clear to prevent infinite errors

# ============================================================
# STATUS FILE - Thread-Safe Atomic Updates
# ============================================================

def update_status(updates):
    """Thread-safe atomic status file update. v3.4.7: cannot raise.

    Three of the steps between the lock and the write used to be unguarded,
    and the two that were guarded reported through App.Console - the one
    thing a third-party patch can take away. Either way the caller, a Qt
    timer slot, got the exception. Now the whole body is guarded and logging
    goes through the console captured at import.
    """
    try:
        with _status_lock:
            status = {}
            if os.path.exists(AI_STATUS_FILE):
                try:
                    with open(AI_STATUS_FILE, 'r') as f:
                        status = json.load(f)
                except Exception as e:
                    _log_warn(f"Could not read status file: {e}\n")
                    status = {}

            try:
                status.update(updates)
            except Exception:
                pass
            status['last_heartbeat'] = datetime.now().isoformat()

            try:
                status.update(_state.get_stats())
            except Exception:
                pass

            # Atomic write via temp file
            try:
                temp_file = f"{AI_STATUS_FILE}.tmp"
                with open(temp_file, 'w') as f:
                    json.dump(status, f, indent=2)
                os.replace(temp_file, AI_STATUS_FILE)
                return True
            except Exception as e:
                _log_warn(f"Cannot update status: {e}\n")
                return False
    except BaseException as e:
        _log_err(f"update_status failed outright: {e}\n")
        return False

def periodic_status_update():
    """Periodic status file update - called by timer.

    v3.4.7: stamps liveness FIRST, so the watchdog can see this timer is
    alive even when the body then fails; catches BaseException rather than
    Exception; and reports through the captured console. Nothing may escape
    into Qt from here.
    """
    _tick('status')
    try:
        update_status(_state.get_stats())
    except BaseException as e:
        _log_err(f"Status update error: {e}\n")
    try:
        # SELF-HEALING: Detect and recover from stuck queue
        detect_and_recover_stuck_queue()
    except BaseException as e:
        _log_err(f"Stuck-queue check error: {e}\n")

def detect_and_recover_stuck_queue():
    """
    Auto-detect stuck queue and recover without restart
    
    Detects:
    - File size growing but position not advancing (stuck queue)
    - More than 5 unprocessed commands in queue (stagnant buildup)
    - Long time since last command processed
    """
    global _last_queue_check_time, _last_queue_size, _stuck_position_count
    
    try:
        if not os.path.exists(AI_INPUT_FILE):
            return
        
        current_time = datetime.now()
        file_size = os.path.getsize(AI_INPUT_FILE)
        current_position = _state.last_position
        
        # Initialize tracking variables if needed
        if '_last_queue_check_time' not in globals():
            globals()['_last_queue_check_time'] = current_time
            globals()['_last_queue_size'] = file_size
            globals()['_stuck_position_count'] = 0
            globals()['_last_checked_position'] = current_position
            return
        
        time_since_check = (current_time - _last_queue_check_time).total_seconds()
        
        # Only check every 30 seconds to avoid false positives
        if time_since_check < 30:
            return
        
        # Count ONLY unprocessed commands (after last_position, not total lines)
        # BUG FIX: Previously counted ALL lines in the file, causing false
        # "stagnant" triggers after ~6 commands and wiping the queue.
        unprocessed_count = 0
        try:
            with open(AI_INPUT_FILE, 'r', encoding='utf-8') as f:
                f.seek(current_position)  # Skip already-processed content
                remaining = f.read()
                lines = remaining.split('\n')
                unprocessed_count = len([line for line in lines if line.strip()])
        except:
            unprocessed_count = 0
        
        # Check if position is stuck while file is growing
        position_unchanged = (current_position == globals().get('_last_checked_position', 0))
        file_growing = file_size > globals().get('_last_queue_size', 0)
        
        # CRITICAL FIX: Ignore position checks if file is smaller than position (queue was cleared)
        queue_was_cleared = file_size < current_position
        if queue_was_cleared:
            # Reset position to start of file
            _state.last_position = 0
            globals()['_stuck_position_count'] = 0
            return  # Skip stuck checks after queue clear
        
        # TRIGGER 1: Position stuck with growing file
        stuck_trigger = position_unchanged and file_growing and file_size > 1024
        
        # TRIGGER 2: More than 5 stagnant commands in queue
        stagnant_trigger = unprocessed_count > 5
        
        if stuck_trigger or stagnant_trigger:
            globals()['_stuck_position_count'] = globals().get('_stuck_position_count', 0) + 1
            
            # Only show warnings if we're about to take action (2nd detection or >10 commands)
            should_clear = (globals()['_stuck_position_count'] >= 2) or (unprocessed_count > 10)
            
            if should_clear:
                if stagnant_trigger:
                    App.Console.PrintWarning(f"[SELF-HEAL] {unprocessed_count} stagnant commands - clearing queue\n")
                if stuck_trigger:
                    App.Console.PrintWarning(f"[SELF-HEAL] Position stuck at {current_position} - clearing queue\n")
            
            if should_clear:
                if unprocessed_count > 10:
                    App.Console.PrintError(f"[SELF-HEAL] {unprocessed_count} commands queued - immediate clear!\n")
                else:
                    App.Console.PrintError("[SELF-HEAL] Stuck queue detected - clearing and resetting!\n")
                
                # Backup current queue
                backup_path = AI_INPUT_FILE + '.stuck_backup'
                try:
                    import shutil
                    shutil.copy2(AI_INPUT_FILE, backup_path)
                    App.Console.PrintMessage(f"[SELF-HEAL] Backed up {unprocessed_count} commands to: {backup_path}\n")
                except:
                    pass
                
                # Clear the queue
                with open(AI_INPUT_FILE, 'w') as f:
                    pass
                
                # Reset position
                _state.last_position = 0
                _state._last_input_mtime = os.path.getmtime(AI_INPUT_FILE)
                
                # Reset stuck counter
                globals()['_stuck_position_count'] = 0
                
                App.Console.PrintMessage("[SELF-HEAL] Queue cleared - ready for new commands\n")
        else:
            # Reset stuck counter if position is advancing and queue is small
            globals()['_stuck_position_count'] = 0
        
        # Update tracking variables
        globals()['_last_queue_check_time'] = current_time
        globals()['_last_queue_size'] = file_size
        globals()['_last_checked_position'] = current_position
        
    except Exception as e:
        App.Console.PrintWarning(f"[QUEUE CHECK] Error during stuck queue detection: {e}\n")

# ============================================================
# HEALTH CHECK SYSTEM
# ============================================================

def update_health_check():
    """Update health check file for external monitoring"""
    try:
        stats = _state.get_stats()
        
        # Determine health status
        health_status = 'healthy'
        issues = []
        
        if not stats['monitoring_active']:
            health_status = 'stopped'
            issues.append('Monitoring not active')
        
        if stats['error_rate'] > 0.5:
            health_status = 'degraded'
            issues.append(f"High error rate: {stats['error_rate']:.1%}")
        
        if stats['consecutive_errors'] >= Config.MAX_CONSECUTIVE_ERRORS:
            health_status = 'critical'
            issues.append(f"Consecutive errors: {stats['consecutive_errors']}")
        
        if stats['last_command_time']:
            last_cmd_time = datetime.fromisoformat(stats['last_command_time'])
            if (datetime.now() - last_cmd_time).seconds > 300:
                health_status = 'stale'
                issues.append('No commands for 5+ minutes')
        
        health = {
            'timestamp': datetime.now().isoformat(),
            'status': health_status,
            'issues': issues,
            'monitoring_active': stats['monitoring_active'],
            'uptime_seconds': stats['uptime_seconds'],
            'commands_processed': stats['commands_processed'],
            'error_rate': stats['error_rate'],
            'last_command_time': stats['last_command_time'],
            'freecad_version': f"{App.Version()[0]}.{App.Version()[1]}",
            'ai_bridge_version': Config.VERSION,
            'system_resources': {
                'input_file_size': os.path.getsize(AI_INPUT_FILE) if os.path.exists(AI_INPUT_FILE) else 0,
                'output_file_size': os.path.getsize(AI_OUTPUT_FILE) if os.path.exists(AI_OUTPUT_FILE) else 0,
                'learning_db_size': os.path.getsize(LEARNING_DB_FILE) if os.path.exists(LEARNING_DB_FILE) else 0
            }
        }
        
        with open(HEALTH_CHECK_FILE, 'w') as f:
            json.dump(health, f, indent=2)
    
    except Exception as e:
        App.Console.PrintError(f"Health check update error: {e}\n")

# ============================================================
# COMMAND PROCESSING - With Position Safety
# ============================================================

def process_ai_commands():
    """
    Process commands with position safety and smart polling
    
    CRITICAL FIX: File position now protected against corruption
    CRITICAL FIX 2: Lock prevents concurrent execution
    CRITICAL FIX 3: Detailed logging to debug loop issue
    
    DUPLICATE PREVENTION MEASURES (v3.0.1):
    ========================================
    1. Non-blocking lock: Only one processing cycle at a time
    2. Command ID tracking: Skip if ID already processed
    3. Content-based deduplication: Hash check prevents same command within 2 seconds
    4. Immediate ID marking: Mark processed BEFORE execution with immediate flush
    5. File system sync: Force OS to flush processed IDs to disk
    6. Post-processing delay: 50ms pause after batch to prevent rapid-fire duplicates
    7. mtime check: Only process if file modified since last check
    
    These measures prevent the race condition where:
    - Timer fires twice in quick succession
    - Same command read before ID is saved
    - File not fully flushed when next cycle reads it
    """
    # Non-blocking lock - if already processing, skip this cycle
    if not _processing_lock.acquire(blocking=False):
        App.Console.PrintWarning("[SKIP] Already processing commands\n")
        return  # Another processing cycle is active, skip
    
    try:
        if not os.path.exists(AI_INPUT_FILE):
            return
        
        # PERFORMANCE OPTIMIZATION: Check mtime before reading
        current_mtime = os.path.getmtime(AI_INPUT_FILE)
        if current_mtime <= _state._last_input_mtime:
            return  # No new data
        # v3.4.6: do NOT commit the mtime here. It used to be recorded at
        # this point - before the file had been read successfully - so any
        # failure below marked this revision of the input as "already seen"
        # and its pending commands became unreachable until something else
        # wrote to the file. Committed at the end of a completed pass
        # instead; see the matching note further down.
        
        # Save starting position for rollback
        start_position = _state.last_position
        
        # v3.3.3: NON-BLOCKING open. Never sleep on the GUI thread. If the input
        # file is momentarily write-locked (PowerShell/connector mid-write), just
        # bail and let the next poll tick (Config.POLL_INTERVAL_MS) retry - this
        # removes the per-poll UI micro-stall that made a locked file feel like a hang.
        f = None
        try:
            f = open(AI_INPUT_FILE, 'r', encoding='utf-8')
        except (PermissionError, OSError):
            return  # locked/unavailable this tick - retry on next poll, no UI stall

        if not f:
            return  # Could not open file
        
        try:
            f.seek(start_position)
            
            # Read line by line, tracking position
            while True:
                line_start = f.tell()
                line = f.readline()
                
                if not line:
                    break  # EOF
                
                line = line.strip()
                if not line:
                    continue
                
                try:
                    # Parse command
                    command_data = json.loads(line)
                    
                    # Validate command structure
                    if not isinstance(command_data, dict):
                        App.Console.PrintWarning(f"Invalid command format at byte {line_start}\n")
                        continue
                    
                    command_type = command_data.get('type', 'execute')
                    # Support both 'id' and 'command_id' keys
                    command_id = command_data.get('command_id') or command_data.get('id')
                    command = command_data.get('command', '')
                    # Multi-AI support: extract agent_id for result routing
                    agent_id = command_data.get('agent_id', None)
                    
                    # Create hash of command content for duplicate detection
                    import hashlib
                    command_hash = hashlib.md5(command.encode('utf-8')).hexdigest() if command else None
                    
                    # ====== v3.4.0 PHASE 8: REGISTRATION HANDSHAKE ======
                    # Any agent connecting to this bridge must review the startup
                    # context before it is allowed to execute. 'hello' hands over
                    # the context + its hash; execution is gated on holding the
                    # CURRENT hash, so a knowledge-base change forces a re-read.
                    #
                    # ORDERING IS DELIBERATE: this block runs BEFORE the duplicate
                    # ID/hash marking below. If a rejected command were marked
                    # processed first, the agent's retry after registering would
                    # carry identical CONTENT and be silently swallowed by the
                    # 30-second content-hash dedup - the command would vanish with
                    # no error anywhere. Rejected commands must leave no trace.
                    if command_type == 'hello':
                        try:
                            _ctx_hash = get_bridge_context_hash()
                            _state.register_agent(agent_id or 'anonymous', _ctx_hash)
                            _ctx_path = os.path.join(AI_IO_DIR, "ai_context_summary.txt")
                            ack = {
                                'type': 'registration_ack',
                                'command_id': command_id,
                                'agent_id': agent_id,
                                'context_hash': _ctx_hash,
                                'context_file': _ctx_path,
                                'core_rules': OLLAMA_CORE_RULES,
                                'bridge_version': Config.VERSION,
                                'timestamp': datetime.now().isoformat(),
                                'note': ('Read context_file before sending commands. '
                                         'Include this context_hash on every command; '
                                         'a changed hash means the knowledge base moved '
                                         'and you must re-register.')
                            }
                            with _result_buffer_lock:
                                _result_buffer.append(ack)
                            App.Console.PrintMessage(
                                f"[REGISTER] Agent '{agent_id}' registered "
                                f"(context {_ctx_hash})\n")
                        except Exception as e:
                            App.Console.PrintError(f"[REGISTER] Handshake failed: {e}\n")
                        continue

                    if (Config.REQUIRE_AGENT_REGISTRATION
                            and command_type in ('execute', 'run_macro')):
                        _ctx_hash = get_bridge_context_hash()
                        if not _state.is_agent_registered(agent_id, _ctx_hash):
                            reject = {
                                'type': 'registration_required',
                                'command_id': command_id,
                                'agent_id': agent_id,
                                'context_hash': _ctx_hash,
                                'context_file': os.path.join(AI_IO_DIR,
                                                             "ai_context_summary.txt"),
                                'core_rules': OLLAMA_CORE_RULES,
                                'timestamp': datetime.now().isoformat(),
                                'reason': ("Agent has not registered, or its context is "
                                           "stale. Send {'type':'hello','agent_id':...} "
                                           "and re-read the context before retrying."),
                            }
                            with _result_buffer_lock:
                                _result_buffer.append(reject)
                            App.Console.PrintWarning(
                                f"[REGISTER] Rejected command from unregistered agent "
                                f"'{agent_id}' - handshake required\n")
                            continue

                    # CRITICAL: Require command_id to prevent duplicates
                    if not command_id:
                        App.Console.PrintWarning(f"[SKIP] Command missing ID at byte {line_start} - cannot prevent duplicates!\n")
                        # Still process but warn - this is dangerous
                    
                    # CRITICAL FIX: Skip if command already processed (by ID)
                    if command_id and _state.is_command_processed(command_id):
                        App.Console.PrintMessage(f"[SKIP] Already processed ID: {command_id[:8]}...\n")
                        continue  # Skip duplicate command
                    
                    # ADDITIONAL CHECK: Skip if exact same command was recently processed (by hash)
                    if command_hash and _state.is_command_hash_recent(command_hash):
                        App.Console.PrintWarning(f"[SKIP] Duplicate command detected (same content recently executed)\n")
                        continue  # Skip duplicate command
                    
                    # CRITICAL: Mark as processed IMMEDIATELY to prevent race conditions
                    # Multiple timer callbacks could read the same command before any marks it processed
                    if command_id:
                        agent_label = f" [{agent_id}]" if agent_id else ""
                        App.Console.PrintMessage(f"[EXEC]{agent_label} Processing command: {command_id[:8]}...\n")
                        _state.mark_command_processed(command_id, command_hash)
                    else:
                        App.Console.PrintWarning(f"[WARN] Executing command without ID - duplicate prevention disabled\n")
                    
                    # Speak command notification
                    if _tts and Config.TTS_SPEAK_COMMANDS:
                        _tts.speak("Executing command")
                    
                    # Process based on type
                    if command_type == 'execute':
                        command = command_data.get('command')
                        if not command:
                            App.Console.PrintWarning(f"Missing command in execute at byte {line_start}\n")
                            continue
                        
                        App.Console.PrintMessage(f"[EXEC] Executing: {command[:50]}...\n")
                        
                        # CRITICAL: Set global flag to block all timers during execution
                        global _executing_command
                        _executing_command = True
                        try:
                            # Start capturing console output BEFORE execution
                            _console_capture.start()

                            # Execute with security and timeout
                            result = _executor.execute_with_timeout(command, command_id)
                            
                            # AUTOMATIC CAPTURE: Do this BEFORE clearing _executing_command flag
                            # to prevent timer from running during capture
                            report_data = capture_report_view_state()
                            result['report_view'] = report_data
                            
                            notification_data = capture_notification_state()
                            result['notifications'] = notification_data
                            
                        finally:
                            _executing_command = False
                        
                        App.Console.PrintMessage(f"[EXEC] Result: success={result.get('success')}\n")
                        
                        # INTELLIGENT AUTO-CORRECTION: Check for FreeCAD warnings even on "success"
                        needs_correction = result.get('needs_correction', False)
                        freecad_warnings = result.get('freecad_warnings', [])
                        freecad_errors = result.get('freecad_errors', [])
                        
                        if needs_correction and _auto_correction:
                            App.Console.PrintWarning(f"[AUTO-CORRECT] Detected issues, attempting fix...\n")
                            for warning in freecad_warnings:
                                App.Console.PrintWarning(f"  Warning: {warning}\n")
                            for error in freecad_errors:
                                App.Console.PrintError(f"  Error: {error}\n")
                            
                            # Get console state
                            console_state = result.get('console_state', {})
                            
                            # Generate corrections
                            corrections = _auto_correction.detect_and_correct(
                                command, console_state, command_id
                            )
                            
                            if corrections:
                                # Sort by confidence
                                corrections.sort(key=lambda x: x.get('confidence', 0), reverse=True)
                                best_correction = corrections[0]
                                
                                App.Console.PrintMessage(f"[AUTO-CORRECT] Found correction (confidence: {best_correction['confidence']:.0%})\n")
                                App.Console.PrintMessage(f"[AUTO-CORRECT] Issue type: {best_correction['type']}\n")
                                
                                # Execute corrected command
                                corrected_cmd = best_correction['corrected_command']
                                App.Console.PrintMessage(f"[AUTO-CORRECT] Retrying with fix...\n")
                                
                                # Mark original as needs_correction in output
                                result['auto_correction_attempted'] = True
                                result['original_warnings'] = freecad_warnings
                                
                                # Execute correction
                                _executing_command = True
                                try:
                                    correction_result = _executor.execute_with_timeout(corrected_cmd, command_id + '_corrected')
                                finally:
                                    _executing_command = False
                                
                                if correction_result.get('success') and not correction_result.get('needs_correction'):
                                    App.Console.PrintMessage(f"[AUTO-CORRECT] Success - issue resolved!\n")
                                    
                                    # Record the successful correction
                                    _learning_system.record_error_resolution(
                                        original_error=' | '.join(freecad_warnings + freecad_errors),
                                        original_command=command,
                                        fixed_command=corrected_cmd,
                                        solution_description=f"Auto-corrected {best_correction['type']}"
                                    )
                                    
                                    # Update result to show correction
                                    result['auto_corrected'] = True
                                    result['corrected_command'] = corrected_cmd
                                    result['correction_result'] = correction_result
                                    
                                    # Speak success
                                    if _tts and Config.TTS_SPEAK_COMMANDS:
                                        _tts.speak("Auto-correction successful")
                                else:
                                    App.Console.PrintWarning(f"[AUTO-CORRECT] Fix did not resolve issue\n")
                                    result['auto_correction_failed'] = True
                                    
                                    # Buffer the failed correction attempt
                                    with _result_buffer_lock:
                                        _result_buffer.append(correction_result)
                            else:
                                App.Console.PrintWarning(f"[AUTO-CORRECT] No automatic fix available\n")
                                result['auto_correction_unavailable'] = True
                        
                        # Log significant report view findings
                        report_data = result.get('report_view', {})
                        if report_data.get('message_count', 0) > 0:
                            recent_messages = report_data.get('messages', [])[-5:]  # Last 5 messages
                            if recent_messages:
                                App.Console.PrintMessage(f"[REPORT] Captured {len(recent_messages)} recent messages\n")
                                for msg in recent_messages:
                                    if 'error' in msg.lower() or 'warning' in msg.lower():
                                        App.Console.PrintWarning(f"  → {msg[:100]}\n")
                        
                        # Log significant notifications
                        notification_data = result.get('notifications', {})
                        if notification_data.get('notification_count', 0) > 0:
                            notifications = notification_data.get('notifications', [])
                            App.Console.PrintMessage(f"[NOTIFY] Captured {len(notifications)} notifications\n")
                            for notif in notifications:
                                if notif.get('type') in ['object_errors', 'document_status']:
                                    App.Console.PrintWarning(f"  → [{notif['type']}] {notif.get('message', '')}\n")
                        
                        # DON'T buffer result - comprehensive report handles output
                        # (Old buffer system overwrites comprehensive reports)
                        
                        # Update statistics
                        if result.get('success'):
                            _state.increment_commands()
                            _state.reset_consecutive_errors()
                            
                            # Write comprehensive report for AI agent (success with output)
                            write_comprehensive_report_for_ai(result, command, command_id, agent_id)
                            
                            # Speak success
                            if _tts and Config.TTS_SPEAK_COMMANDS and not needs_correction:
                                _tts.speak_command_result(True)
                            
                            # Learn from success (use corrected command if available)
                            if not needs_correction or result.get('auto_corrected'):
                                try:
                                    _learning_system.record_success(
                                        command=result.get('corrected_command', command),
                                        description=f"Command executed successfully" + (" (auto-corrected)" if result.get('auto_corrected') else ""),
                                        category="execution",
                                        # v3.4.0: provenance - local-model output is
                                        # stored unverified until a human promotes it
                                        source_agent=agent_id or "unknown"
                                    )
                                except Exception as e:
                                    App.Console.PrintWarning(f"Learning system error: {e}\n")
                                    pass
                            
                            # Check if this success was a fix for a previous error
                            try:
                                fix_result = _error_fix_tracker.check_for_fix(command)
                                if fix_result:
                                    # Record the error→fix pair in learning database
                                    _learning_system.record_error_resolution(
                                        original_error=fix_result['original_error'],
                                        original_command=fix_result['original_command'],
                                        fixed_command=fix_result['fixed_command'],
                                        solution_description=fix_result['solution']
                                    )
                                    App.Console.PrintMessage(f"\n{'='*70}\n")
                                    App.Console.PrintMessage(f"[LEARNED] Error→Fix pair recorded!\n")
                                    App.Console.PrintMessage(f"  Error: {fix_result['error_type']}\n")
                                    App.Console.PrintMessage(f"  Solution: {fix_result['solution']}\n")
                                    App.Console.PrintMessage(f"{'='*70}\n\n")
                            except Exception as e:
                                App.Console.PrintWarning(f"Error fix tracking failed: {e}\n")
                        else:
                            _state.increment_errors()
                            
                            # Speak error
                            if _tts and Config.TTS_SPEAK_ERRORS:
                                error_msg = result.get('error', 'Unknown error')
                                _tts.speak_command_result(False)
                            
                            # Log error with context
                            log_error_with_context(
                                result.get('error', 'Unknown error'),
                                command_id,
                                command,
                                {'security_blocked': result.get('security_blocked', False),
                                 'timeout': result.get('timeout', False),
                                 'traceback': result.get('traceback')}
                            )
                            
                            # Print prominent error
                            App.Console.PrintError(f"\n{'='*70}\n")
                            App.Console.PrintError(f"[ERROR] COMMAND FAILED: {command_id}\n")
                            App.Console.PrintError(f"Error: {result['error']}\n")
                            App.Console.PrintError(f"{'='*70}\n\n")
                            
                            # Track error for potential fix learning
                            error_text = result.get('error', 'Unknown error')
                            error_type = error_text.split(':')[0] if ':' in error_text else 'Error'
                            _error_fix_tracker.record_error(command_id, command, error_text, error_type)
                            
                            # Write comprehensive error report for AI agent
                            write_comprehensive_report_for_ai(result, command, command_id, agent_id)
                    
                    elif command_type == 'query_selection':
                        selection_data = capture_selection_state()
                        resp = {
                            'type': 'selection_query_result',
                            'command_id': command_id,
                            'data': selection_data,
                            'timestamp': datetime.now().isoformat()
                        }
                        if agent_id:
                            resp['agent_id'] = agent_id
                        with _result_buffer_lock:
                            _result_buffer.append(resp)

                    elif command_type == 'query_report':
                        report_data = capture_report_view_state()
                        resp = {
                            'type': 'report_query_result',
                            'command_id': command_id,
                            'data': report_data,
                            'timestamp': datetime.now().isoformat()
                        }
                        if agent_id:
                            resp['agent_id'] = agent_id
                        with _result_buffer_lock:
                            _result_buffer.append(resp)

                    elif command_type == 'query_notifications':
                        notification_data = capture_notification_state()
                        resp = {
                            'type': 'notification_query_result',
                            'command_id': command_id,
                            'data': notification_data,
                            'timestamp': datetime.now().isoformat()
                        }
                        if agent_id:
                            resp['agent_id'] = agent_id
                        with _result_buffer_lock:
                            _result_buffer.append(resp)

                    elif command_type == 'ping':
                        resp = {
                            'type': 'pong',
                            'command_id': command_id,
                            'timestamp': datetime.now().isoformat()
                        }
                        if agent_id:
                            resp['agent_id'] = agent_id
                        with _result_buffer_lock:
                            _result_buffer.append(resp)

                    elif command_type == 'system_test':
                        test_results = run_system_test()
                        resp = {
                            'type': 'system_test_result',
                            'command_id': command_id,
                            'results': test_results,
                            'timestamp': datetime.now().isoformat()
                        }
                        if agent_id:
                            resp['agent_id'] = agent_id
                        with _result_buffer_lock:
                            _result_buffer.append(resp)
                    
                    elif command_type == 'correct_command':
                        # AI is providing a correction for a previous failed command
                        original_id = command_data.get('original_command_id')
                        corrected_cmd = command_data.get('corrected_command')
                        reason = command_data.get('reason', 'AI correction')
                        
                        App.Console.PrintMessage(f"[AI-CORRECT] Applying correction for command {original_id}\n")
                        App.Console.PrintMessage(f"[AI-CORRECT] Reason: {reason}\n")
                        
                        # Execute corrected command
                        _executing_command = True
                        try:
                            result = _executor.execute_with_timeout(corrected_cmd, command_id)
                        finally:
                            _executing_command = False
                        
                        # Check result
                        if result.get('success') and not result.get('needs_correction'):
                            App.Console.PrintMessage(f"[AI-CORRECT] ✓ Correction successful!\n")
                            
                            # Record the successful correction in learning system
                            try:
                                _learning_system.record_error_resolution(
                                    original_error=f"Command {original_id} failed",
                                    original_command="(see previous error report)",
                                    fixed_command=corrected_cmd,
                                    solution_description=reason
                                )
                            except Exception as e:
                                App.Console.PrintWarning(f"Could not record correction: {e}\n")
                            
                            # Write success report
                            resp = {
                                'type': 'correction_success',
                                'command_id': command_id,
                                'original_command_id': original_id,
                                'corrected_command': corrected_cmd[:200],
                                'reason': reason,
                                'result': result.get('output', {}),
                                'timestamp': datetime.now().isoformat()
                            }
                            if agent_id:
                                resp['agent_id'] = agent_id
                            with _result_buffer_lock:
                                _result_buffer.append(resp)
                            
                            # Speak success
                            if _tts and Config.TTS_SPEAK_COMMANDS:
                                _tts.speak("Correction successful")
                        else:
                            App.Console.PrintWarning(f"[AI-CORRECT] ✗ Correction failed\n")
                            
                            # Write failure report
                            resp = {
                                'type': 'correction_failure',
                                'command_id': command_id,
                                'original_command_id': original_id,
                                'error': result.get('error', 'Unknown error'),
                                'timestamp': datetime.now().isoformat()
                            }
                            if agent_id:
                                resp['agent_id'] = agent_id
                            with _result_buffer_lock:
                                _result_buffer.append(resp)
                            
                            # Speak error
                            if _tts and Config.TTS_SPEAK_ERRORS:
                                _tts.speak("Correction failed")
                    
                    elif command_type == 'run_macro':
                        # Safe macro execution — runs an .FCMacro file by path
                        # without requiring exec() or open() in user commands.
                        # Only .FCMacro and .py files under Macro_Directory are allowed.
                        macro_path = command_data.get('macro_path', '')
                        App.Console.PrintMessage(f"[MACRO] Run request: {macro_path}\n")

                        # v3.5.2: the roots are derived from FreeCAD rather
                        # than naming one machine's folder, and containment
                        # is tested on a path boundary. See
                        # validate_macro_path() and _default_allowed_roots().
                        import os.path as _osp
                        path_ok, _why, norm_path = validate_macro_path(
                            macro_path)

                        if not path_ok:
                            resp = {
                                'type': 'macro_error',
                                'command_id': command_id,
                                'success': False,
                                'error': f"Macro path rejected: {_why}",
                                'timestamp': datetime.now().isoformat()
                            }
                            if agent_id:
                                resp['agent_id'] = agent_id
                            with _result_buffer_lock:
                                _result_buffer.append(resp)
                        else:
                            # Execute macro via importlib (bypasses exec/open sandbox safely)
                            import importlib.util, importlib.machinery
                            _executing_command = True
                            _console_capture.start()
                            try:
                                loader = importlib.machinery.SourceFileLoader('_bridge_macro', norm_path)
                                spec = importlib.util.spec_from_file_location(
                                    '_bridge_macro', norm_path, loader=loader)
                                mod = importlib.util.module_from_spec(spec)
                                spec.loader.exec_module(mod)
                                App.Console.PrintMessage(f"[MACRO] Executed: {_osp.basename(norm_path)}\n")

                                captured = _console_capture.stop()
                                resp = {
                                    'type': 'macro_result',
                                    'command_id': command_id,
                                    'success': True,
                                    'macro': _osp.basename(norm_path),
                                    'timestamp': datetime.now().isoformat()
                                }
                                # Include captured Report View messages
                                if captured.get('messages') or captured.get('warnings') or captured.get('errors'):
                                    resp['report_view'] = {
                                        'timestamp': datetime.now().isoformat(),
                                        'message_count': len(captured.get('messages', [])) + len(captured.get('warnings', [])) + len(captured.get('errors', [])),
                                        'messages': (
                                            [f"[MSG] {m}" for m in captured.get('messages', [])[-30:]] +
                                            [f"[WARN] {w}" for w in captured.get('warnings', [])[-10:]] +
                                            [f"[ERR] {e}" for e in captured.get('errors', [])[-10:]]
                                        )
                                    }
                            except Exception as me:
                                _console_capture.stop()
                                App.Console.PrintError(f"[MACRO] Failed: {me}\n")
                                resp = {
                                    'type': 'macro_error',
                                    'command_id': command_id,
                                    'success': False,
                                    'error': str(me),
                                    'timestamp': datetime.now().isoformat()
                                }
                            finally:
                                _executing_command = False
                            if agent_id:
                                resp['agent_id'] = agent_id
                            with _result_buffer_lock:
                                _result_buffer.append(resp)

                    else:
                        App.Console.PrintWarning(f"Unknown command type: {command_type}\n")
                
                except json.JSONDecodeError as e:
                    App.Console.PrintWarning(f"Invalid JSON at byte {line_start}: {e}\n")
                    continue
                
                except Exception as e:
                    App.Console.PrintError(f"Command processing error at byte {line_start}: {e}\n")
                    log_error_with_context(e, None, line, {'byte_position': line_start})
                    # Don't break - try to continue with next command
            
            # Update position to end of file after successful processing
            _state.last_position = f.tell()

            # v3.4.6: only now is this revision of the input genuinely
            # consumed - see the note at the mtime check above.
            _state._last_input_mtime = current_mtime

            # v3.3.3: removed the 50ms GUI-thread sleep here. Duplicate protection
            # is already covered by mtime + command-ID + content-hash dedup, so this
            # delay only added a stall to every poll that processed a command.
        finally:
            f.close()  # Always close the file
    
    except Exception as e:
        # v3.4.6 - POISON-PILL FIX. This used to leave _state.last_position
        # untouched on purpose. Combined with the mtime gate above, that
        # permanently wedged the reader on one bad command while every
        # health signal still read healthy. See the v3.4.6 header note.
        #
        # Skipping unread input is a real cost - a good command queued
        # behind a bad one is lost. Being unreachable with a healthy
        # heartbeat is a worse one, because nothing surfaces it.
        # RECOVERY RUNS FIRST, and nothing below may be able to prevent
        # it. An earlier draft of this fix put the logging call ahead of
        # the recovery; a failure inside the logger then skipped the
        # rescue entirely and the reader stayed wedged - a handler meant
        # to un-wedge the bridge wedging it instead. Caught by the test,
        # not by reading it. Every step below is independently guarded.
        skipped = 0
        try:
            end_of_input = os.path.getsize(AI_INPUT_FILE)
            skipped = max(0, end_of_input - _state.last_position)
            _state.last_position = end_of_input
            _state._last_input_mtime = os.path.getmtime(AI_INPUT_FILE)
        except Exception:
            pass

        try:
            App.Console.PrintError(f"Fatal error in command processor: {e}\n")
            if skipped:
                App.Console.PrintError(
                    f"[RECOVER] Skipped {skipped} unprocessed byte(s) of input "
                    f"so the bridge does not wedge on them. Re-send anything "
                    f"that went unanswered.\n"
                )
        except Exception:
            pass

        try:
            log_error_with_context(e, None, "process_ai_commands", None)
        except Exception:
            pass

        try:
            update_status({
                'error_state': True,
                'last_error': f"processor fatal: {e} (skipped {skipped} bytes)",
            })
        except Exception:
            pass
    finally:
        _processing_lock.release()  # Always release the lock

# ============================================================
# SYSTEM TEST FUNCTION - ADVANCED SUITE
# ============================================================
# Comprehensive tests derived from Technical_Data knowledge base
# Tests: Part Module, Boolean Ops, Geometry, Wire/Face creation,
#        Knowledge base integrity, Error→Fix learning, and more
# ============================================================

def run_system_test():
    """
    ADVANCED Comprehensive system test for the AI Bridge
    Derived from Technical_Data learning resources:
    - Part_Scripting_Reference.txt (900 lines)
    - Python_Scripting_Conventions.txt
    - Expressions_Reference.txt
    - FreeCAD_Knowledge_Base.json (285 patterns)
    Returns detailed results of all tests
    """
    tests = []
    passed = 0
    failed = 0
    
    # ========================================================================
    # CATEGORY 1: CORE INFRASTRUCTURE TESTS (1-8)
    # ========================================================================
    
    # Test 1: Basic Python Execution
    try:
        result = _executor.execute_with_timeout('1 + 1', 'test_basic')
        if result.get('success'):
            tests.append({'name': '1. Basic Execution', 'passed': True, 'category': 'Core'})
            passed += 1
        else:
            tests.append({'name': '1. Basic Execution', 'passed': False, 'error': result.get('error'), 'category': 'Core'})
            failed += 1
    except Exception as e:
        tests.append({'name': '1. Basic Execution', 'passed': False, 'error': str(e), 'category': 'Core'})
        failed += 1
    
    # Test 2: Error Handling (Division by Zero)
    try:
        result = _executor.execute_with_timeout('1/0', 'test_error')
        if not result.get('success') and result.get('error'):
            tests.append({'name': '2. Error Handling', 'passed': True, 'category': 'Core'})
            passed += 1
        else:
            tests.append({'name': '2. Error Handling', 'passed': False, 'category': 'Core'})
            failed += 1
    except Exception as e:
        tests.append({'name': '2. Error Handling', 'passed': False, 'error': str(e), 'category': 'Core'})
        failed += 1
    
    # Test 3: Security Blocking (import os must be blocked)
    try:
        result = _executor.execute_with_timeout('import os', 'test_security')
        if result.get('security_blocked'):
            tests.append({'name': '3. Security Blocking', 'passed': True, 'category': 'Core'})
            passed += 1
        else:
            tests.append({'name': '3. Security Blocking', 'passed': False, 'category': 'Core'})
            failed += 1
    except Exception as e:
        tests.append({'name': '3. Security Blocking', 'passed': False, 'error': str(e), 'category': 'Core'})
        failed += 1
    
    # Test 4: File I/O Paths Exist
    try:
        io_ok = os.path.exists(AI_INPUT_FILE) and os.path.exists(AI_OUTPUT_FILE)
        tests.append({'name': '4. File I/O Paths', 'passed': io_ok, 'category': 'Core'})
        passed += 1 if io_ok else 0
        failed += 0 if io_ok else 1
    except Exception as e:
        tests.append({'name': '4. File I/O Paths', 'passed': False, 'error': str(e), 'category': 'Core'})
        failed += 1
    
    # Test 5: Learning System Integrity
    try:
        stats = _learning_system.get_stats()
        learning_ok = isinstance(stats, dict) and 'total_patterns' in stats
        pattern_count = stats.get('total_patterns', 0) if learning_ok else 0
        tests.append({'name': '5. Learning System', 'passed': learning_ok, 'patterns': pattern_count, 'category': 'Core'})
        passed += 1 if learning_ok else 0
        failed += 0 if learning_ok else 1
    except Exception as e:
        tests.append({'name': '5. Learning System', 'passed': False, 'error': str(e), 'category': 'Core'})
        failed += 1
    
    # Test 6: Status Update System
    try:
        status_ok = update_status({'test': True})
        tests.append({'name': '6. Status Updates', 'passed': status_ok, 'category': 'Core'})
        passed += 1 if status_ok else 0
        failed += 0 if status_ok else 1
    except Exception as e:
        tests.append({'name': '6. Status Updates', 'passed': False, 'error': str(e), 'category': 'Core'})
        failed += 1
    
    # Test 7: FreeCAD App Module + Version
    try:
        version = f"{App.Version()[0]}.{App.Version()[1]}"
        tests.append({'name': '7. FreeCAD App Module', 'passed': True, 'version': version, 'category': 'Core'})
        passed += 1
    except Exception as e:
        tests.append({'name': '7. FreeCAD App Module', 'passed': False, 'error': str(e), 'category': 'Core'})
        failed += 1
    
    # Test 8: GUI Selection Module
    try:
        _ = Gui.Selection.getSelection()
        tests.append({'name': '8. GUI Selection', 'passed': True, 'category': 'Core'})
        passed += 1
    except Exception as e:
        tests.append({'name': '8. GUI Selection', 'passed': False, 'error': str(e), 'category': 'Core'})
        failed += 1
    
    # ========================================================================
    # CATEGORY 2: PART MODULE GEOMETRY TESTS (9-16)
    # From Part_Scripting_Reference.txt - Create real shapes in memory
    # ========================================================================
    
    # Test 9: Part.makeBox - Basic 3D Solid Creation
    try:
        import Part
        box = Part.makeBox(10, 20, 30)
        # Verify it's a valid Solid with correct properties
        is_solid = box.ShapeType == 'Solid'
        has_faces = len(box.Faces) == 6
        has_edges = len(box.Edges) == 12
        has_vertices = len(box.Vertexes) == 8
        box_ok = is_solid and has_faces and has_edges and has_vertices
        tests.append({'name': '9. Part.makeBox Geometry', 'passed': box_ok, 
                     'details': f'Solid:{is_solid} Faces:{len(box.Faces)} Edges:{len(box.Edges)} Verts:{len(box.Vertexes)}',
                     'category': 'Geometry'})
        passed += 1 if box_ok else 0
        failed += 0 if box_ok else 1
    except Exception as e:
        tests.append({'name': '9. Part.makeBox Geometry', 'passed': False, 'error': str(e), 'category': 'Geometry'})
        failed += 1
    
    # Test 10: Part.makeSphere - Curved Surface Creation
    try:
        import Part
        sphere = Part.makeSphere(15)
        is_solid = sphere.ShapeType == 'Solid'
        has_face = len(sphere.Faces) == 1
        # Sphere area should be ~4*pi*r^2 = 4*3.14159*225 ≈ 2827
        import math
        expected_area = 4 * math.pi * 15 * 15
        actual_area = sphere.Area
        area_ok = abs(actual_area - expected_area) < 1  # within 1 mm²
        sphere_ok = is_solid and has_face and area_ok
        tests.append({'name': '10. Part.makeSphere Geometry', 'passed': sphere_ok,
                     'details': f'Area: {actual_area:.1f} (expected ~{expected_area:.1f})',
                     'category': 'Geometry'})
        passed += 1 if sphere_ok else 0
        failed += 0 if sphere_ok else 1
    except Exception as e:
        tests.append({'name': '10. Part.makeSphere Geometry', 'passed': False, 'error': str(e), 'category': 'Geometry'})
        failed += 1
    
    # Test 11: Part.makeCylinder - Combined with Volume Check
    try:
        import Part
        import math
        cyl = Part.makeCylinder(5, 20)  # r=5, h=20
        is_solid = cyl.ShapeType == 'Solid'
        # Volume = pi * r^2 * h = pi * 25 * 20 ≈ 1570.8
        expected_vol = math.pi * 25 * 20
        actual_vol = cyl.Volume
        vol_ok = abs(actual_vol - expected_vol) < 0.1
        cyl_ok = is_solid and vol_ok
        tests.append({'name': '11. Part.makeCylinder Volume', 'passed': cyl_ok,
                     'details': f'Volume: {actual_vol:.2f} (expected {expected_vol:.2f})',
                     'category': 'Geometry'})
        passed += 1 if cyl_ok else 0
        failed += 0 if cyl_ok else 1
    except Exception as e:
        tests.append({'name': '11. Part.makeCylinder Volume', 'passed': False, 'error': str(e), 'category': 'Geometry'})
        failed += 1
    
    # Test 12: Boolean Fuse Operation - Union of Two Shapes
    try:
        import Part
        box1 = Part.makeBox(10, 10, 10)
        box2 = Part.makeBox(10, 10, 10, App.Vector(5, 5, 5))
        fused = box1.fuse(box2)
        is_valid = fused.isValid()
        # Fuse can return Solid or Compound - both are valid
        is_shape = fused.ShapeType in ('Solid', 'Compound')
        # Fused volume should be less than 2000 (overlapping cubes)
        vol_ok = 1000 < fused.Volume < 2000
        fuse_ok = is_valid and is_shape and vol_ok
        tests.append({'name': '12. Boolean Fuse Operation', 'passed': fuse_ok,
                     'details': f'Valid:{is_valid} Type:{fused.ShapeType} Volume:{fused.Volume:.0f}',
                     'category': 'Geometry'})
        passed += 1 if fuse_ok else 0
        failed += 0 if fuse_ok else 1
    except Exception as e:
        tests.append({'name': '12. Boolean Fuse Operation', 'passed': False, 'error': str(e), 'category': 'Geometry'})
        failed += 1
    
    # Test 13: Boolean Cut Operation - Subtraction
    try:
        import Part
        base = Part.makeBox(20, 20, 20)
        tool = Part.makeCylinder(5, 30, App.Vector(10, 10, -5))  # Through-hole
        cut_result = base.cut(tool)
        is_valid = cut_result.isValid()
        # Volume should be less than 8000 (cube minus cylinder)
        vol_reduced = cut_result.Volume < 8000
        cut_ok = is_valid and vol_reduced
        tests.append({'name': '13. Boolean Cut Operation', 'passed': cut_ok,
                     'details': f'Volume after cut: {cut_result.Volume:.0f}',
                     'category': 'Geometry'})
        passed += 1 if cut_ok else 0
        failed += 0 if cut_ok else 1
    except Exception as e:
        tests.append({'name': '13. Boolean Cut Operation', 'passed': False, 'error': str(e), 'category': 'Geometry'})
        failed += 1
    
    # Test 14: Wire and Face Creation from Vectors
    try:
        import Part
        # Create a closed rectangular wire
        v1 = App.Vector(0, 0, 0)
        v2 = App.Vector(100, 0, 0)
        v3 = App.Vector(100, 50, 0)
        v4 = App.Vector(0, 50, 0)
        wire = Part.makePolygon([v1, v2, v3, v4, v1])
        is_closed = wire.isClosed()
        face = Part.Face(wire)
        face_area = face.Area  # Should be 100*50 = 5000
        area_ok = abs(face_area - 5000) < 0.01
        wire_ok = is_closed and area_ok
        tests.append({'name': '14. Wire→Face Creation', 'passed': wire_ok,
                     'details': f'Closed:{is_closed} Area:{face_area:.0f}',
                     'category': 'Geometry'})
        passed += 1 if wire_ok else 0
        failed += 0 if wire_ok else 1
    except Exception as e:
        tests.append({'name': '14. Wire→Face Creation', 'passed': False, 'error': str(e), 'category': 'Geometry'})
        failed += 1
    
    # Test 15: Extrusion - Face to Solid
    try:
        import Part
        # Create profile and extrude
        v1, v2, v3, v4 = App.Vector(0,0,0), App.Vector(10,0,0), App.Vector(10,10,0), App.Vector(0,10,0)
        wire = Part.makePolygon([v1, v2, v3, v4, v1])
        face = Part.Face(wire)
        solid = face.extrude(App.Vector(0, 0, 25))
        is_solid = solid.ShapeType == 'Solid'
        # Volume = 10*10*25 = 2500
        vol_ok = abs(solid.Volume - 2500) < 0.1
        extrude_ok = is_solid and vol_ok
        tests.append({'name': '15. Face Extrusion→Solid', 'passed': extrude_ok,
                     'details': f'Volume: {solid.Volume:.0f}',
                     'category': 'Geometry'})
        passed += 1 if extrude_ok else 0
        failed += 0 if extrude_ok else 1
    except Exception as e:
        tests.append({'name': '15. Face Extrusion→Solid', 'passed': False, 'error': str(e), 'category': 'Geometry'})
        failed += 1
    
    # Test 16: BSpline Curve Creation (Advanced)
    try:
        import Part
        # Create BSpline through control points
        points = [App.Vector(0,0,0), App.Vector(10,20,0), App.Vector(30,20,0), 
                  App.Vector(40,0,0), App.Vector(50,0,0)]
        bspline = Part.BSplineCurve()
        bspline.interpolate(points)
        edge = Part.Edge(bspline)
        has_length = edge.Length > 0
        curve_type = str(type(edge.Curve).__name__)
        bspline_ok = has_length and 'BSpline' in curve_type
        tests.append({'name': '16. BSpline Curve Creation', 'passed': bspline_ok,
                     'details': f'Length:{edge.Length:.1f} Type:{curve_type}',
                     'category': 'Geometry'})
        passed += 1 if bspline_ok else 0
        failed += 0 if bspline_ok else 1
    except Exception as e:
        tests.append({'name': '16. BSpline Curve Creation', 'passed': False, 'error': str(e), 'category': 'Geometry'})
        failed += 1
    
    # ========================================================================
    # CATEGORY 3: KNOWLEDGE BASE & LEARNING TESTS (17-22)
    # ========================================================================
    
    # Test 17: AI Documentation Files (Essential for AI Agent)
    try:
        # v3.5.2: found by walking up from this macro. '' if absent, and
        # every caller below already copes with a missing file.
        tech_data_dir = library_dir()   # v4.0.11: honours the setting
        required_docs = [
            'README.txt', 'INDEX.txt', 'Document_Creation_Reference.txt',
            'Expressions_Reference.txt', 'Python_Scripting_Conventions.txt',
            'Part_Scripting_Reference.txt', 'GUI_Creation_Reference.txt'
        ]
        missing_docs = [d for d in required_docs if not os.path.exists(os.path.join(tech_data_dir, d))]
        docs_ok = len(missing_docs) == 0
        tests.append({'name': '17. AI Documentation Files', 'passed': docs_ok,
                     'found': len(required_docs) - len(missing_docs), 'missing': missing_docs,
                     'category': 'Knowledge'})
        passed += 1 if docs_ok else 0
        failed += 0 if docs_ok else 1
    except Exception as e:
        tests.append({'name': '17. AI Documentation Files', 'passed': False, 'error': str(e), 'category': 'Knowledge'})
        failed += 1
    
    # Test 18: FreeCAD Knowledge Base JSON (285 patterns)
    try:
        import json
        kb_path = (library_file("FreeCAD_Knowledge_Base.json")
                   or os.path.join(library_dir(),
                                   "FreeCAD_Knowledge_Base.json"))
        with open(kb_path, 'r', encoding='utf-8') as f:
            kb = json.load(f)
        has_metadata = 'metadata' in kb
        has_patterns = kb.get('metadata', {}).get('total_patterns', 0) >= 100
        has_quick_ref = 'quick_reference' in kb
        kb_ok = has_metadata and has_patterns and has_quick_ref
        pattern_count = kb.get('metadata', {}).get('total_patterns', 0)
        tests.append({'name': '18. FreeCAD Knowledge Base', 'passed': kb_ok,
                     'patterns': pattern_count, 'category': 'Knowledge'})
        passed += 1 if kb_ok else 0
        failed += 0 if kb_ok else 1
    except Exception as e:
        tests.append({'name': '18. FreeCAD Knowledge Base', 'passed': False, 'error': str(e), 'category': 'Knowledge'})
        failed += 1
    
    # Test 19: Community Knowledge Directory Structure
    try:
        ck_dir = os.path.join(library_dir(), "Community_Knowledge")
        required_subdirs = ['Verified', 'Pending', 'Submissions']
        missing_subdirs = [d for d in required_subdirs if not os.path.isdir(os.path.join(ck_dir, d))]
        ck_ok = len(missing_subdirs) == 0
        tests.append({'name': '19. Community Knowledge Dirs', 'passed': ck_ok,
                     'found': len(required_subdirs) - len(missing_subdirs),
                     'category': 'Knowledge'})
        passed += 1 if ck_ok else 0
        failed += 0 if ck_ok else 1
    except Exception as e:
        tests.append({'name': '19. Community Knowledge Dirs', 'passed': False, 'error': str(e), 'category': 'Knowledge'})
        failed += 1
    
    # Test 20: Error→Fix Tracker Functionality
    try:
        tracker_exists = _error_fix_tracker is not None
        has_record = hasattr(_error_fix_tracker, 'record_error')
        has_check = hasattr(_error_fix_tracker, 'check_for_fix')
        tracker_ok = tracker_exists and has_record and has_check
        tests.append({'name': '20. Error→Fix Tracker', 'passed': tracker_ok,
                     'category': 'Knowledge'})
        passed += 1 if tracker_ok else 0
        failed += 0 if tracker_ok else 1
    except Exception as e:
        tests.append({'name': '20. Error→Fix Tracker', 'passed': False, 'error': str(e), 'category': 'Knowledge'})
        failed += 1
    
    # Test 21: Learning Database Writable
    try:
        db_path = os.path.join(LEARNING_DIR, 'AI_Learning_Database.json')
        db_exists = os.path.exists(db_path)
        if db_exists:
            import json
            with open(db_path, 'r', encoding='utf-8') as f:
                db = json.load(f)
            # Accept any valid JSON structure with patterns OR corrections
            has_patterns = 'patterns' in db or 'successful_commands' in db
            has_fixes = 'error_fix_pairs' in db or 'corrections' in db or 'learned_fixes' in db
            db_ok = has_patterns or has_fixes or len(db) > 0  # Any valid content
        else:
            db_ok = False
        tests.append({'name': '21. Learning Database', 'passed': db_ok,
                     'exists': db_exists, 'keys': list(db.keys()) if db_exists else [],
                     'category': 'Knowledge'})
        passed += 1 if db_ok else 0
        failed += 0 if db_ok else 1
    except Exception as e:
        tests.append({'name': '21. Learning Database', 'passed': False, 'error': str(e), 'category': 'Knowledge'})
        failed += 1
    
    # Test 22: TechDataReviewer Search Capability
    try:
        # Check if TechDataReviewer class exists and has required methods
        reviewer_class_ok = 'TechDataReviewer' in globals() or 'TechDataReviewer' in dir()
        if reviewer_class_ok:
            # Check the class has the required methods
            has_search = hasattr(TechDataReviewer, 'search_for_error')
            has_suggest = hasattr(TechDataReviewer, 'suggest_fix') or hasattr(TechDataReviewer, 'get_suggestions')
            reviewer_ok = has_search or has_suggest
        else:
            reviewer_ok = False
        tests.append({'name': '22. TechData Reviewer', 'passed': reviewer_ok,
                     'class_exists': reviewer_class_ok, 'category': 'Knowledge'})
        passed += 1 if reviewer_ok else 0
        failed += 0 if reviewer_ok else 1
    except Exception as e:
        tests.append({'name': '22. TechData Reviewer', 'passed': False, 'error': str(e), 'category': 'Knowledge'})
        failed += 1
    
    # ========================================================================
    # CATEGORY 4: ADVANCED GEOMETRY & TRANSFORMATION TESTS (23-28)
    # From Part_Scripting_Reference.txt - Transformations section
    # ========================================================================
    
    # Test 23: Shape Translation
    try:
        import Part
        box = Part.makeBox(10, 10, 10)
        original_center = box.CenterOfMass
        box.translate(App.Vector(100, 200, 300))
        new_center = box.CenterOfMass
        # Center should have moved by exactly (100, 200, 300)
        dx = new_center.x - original_center.x
        dy = new_center.y - original_center.y
        dz = new_center.z - original_center.z
        translate_ok = abs(dx - 100) < 0.01 and abs(dy - 200) < 0.01 and abs(dz - 300) < 0.01
        tests.append({'name': '23. Shape Translation', 'passed': translate_ok,
                     'details': f'Moved ({dx:.0f},{dy:.0f},{dz:.0f})',
                     'category': 'Transform'})
        passed += 1 if translate_ok else 0
        failed += 0 if translate_ok else 1
    except Exception as e:
        tests.append({'name': '23. Shape Translation', 'passed': False, 'error': str(e), 'category': 'Transform'})
        failed += 1
    
    # Test 24: Shape Rotation (45° around Z-axis)
    try:
        import Part
        import math
        box = Part.makeBox(10, 10, 10)
        # Use BoundBox diagonal to verify rotation (more reliable than vertex index)
        original_bb = box.BoundBox
        orig_diagonal = math.sqrt(original_bb.XLength**2 + original_bb.YLength**2)
        box.rotate(App.Vector(0, 0, 0), App.Vector(0, 0, 1), 45)
        rotated_bb = box.BoundBox
        # After 45° rotation, BoundBox should expand (rotated square inscribed in larger square)
        # For a 10x10 box rotated 45°, new BB should be ~14.14 x 14.14
        expected_size = 10 * math.sqrt(2)  # ~14.14
        x_ok = abs(rotated_bb.XLength - expected_size) < 0.5
        y_ok = abs(rotated_bb.YLength - expected_size) < 0.5
        z_ok = abs(rotated_bb.ZLength - 10) < 0.01  # Z unchanged
        rotate_ok = x_ok and y_ok and z_ok
        tests.append({'name': '24. Shape Rotation', 'passed': rotate_ok,
                     'details': f'Rotated BB: {rotated_bb.XLength:.1f}x{rotated_bb.YLength:.1f}x{rotated_bb.ZLength:.1f} (expected ~14.1x14.1x10)',
                     'category': 'Transform'})
        passed += 1 if rotate_ok else 0
        failed += 0 if rotate_ok else 1
    except Exception as e:
        tests.append({'name': '24. Shape Rotation', 'passed': False, 'error': str(e), 'category': 'Transform'})
        failed += 1
    
    # Test 25: Shape Scaling
    try:
        import Part
        box = Part.makeBox(10, 10, 10)
        original_vol = box.Volume  # 1000
        box.scale(2.0, App.Vector(0, 0, 0))
        new_vol = box.Volume  # Should be 8000 (2^3 * 1000)
        scale_ok = abs(new_vol - 8000) < 0.1
        tests.append({'name': '25. Shape Scaling', 'passed': scale_ok,
                     'details': f'Volume: {original_vol:.0f} → {new_vol:.0f}',
                     'category': 'Transform'})
        passed += 1 if scale_ok else 0
        failed += 0 if scale_ok else 1
    except Exception as e:
        tests.append({'name': '25. Shape Scaling', 'passed': False, 'error': str(e), 'category': 'Transform'})
        failed += 1
    
    # Test 26: BoundBox Analysis
    try:
        import Part
        box = Part.makeBox(30, 40, 50, App.Vector(10, 20, 30))
        bb = box.BoundBox
        x_ok = abs(bb.XMin - 10) < 0.01 and abs(bb.XMax - 40) < 0.01
        y_ok = abs(bb.YMin - 20) < 0.01 and abs(bb.YMax - 60) < 0.01
        z_ok = abs(bb.ZMin - 30) < 0.01 and abs(bb.ZMax - 80) < 0.01
        bb_ok = x_ok and y_ok and z_ok
        tests.append({'name': '26. BoundBox Analysis', 'passed': bb_ok,
                     'details': f'X:{bb.XMin:.0f}-{bb.XMax:.0f} Y:{bb.YMin:.0f}-{bb.YMax:.0f} Z:{bb.ZMin:.0f}-{bb.ZMax:.0f}',
                     'category': 'Transform'})
        passed += 1 if bb_ok else 0
        failed += 0 if bb_ok else 1
    except Exception as e:
        tests.append({'name': '26. BoundBox Analysis', 'passed': False, 'error': str(e), 'category': 'Transform'})
        failed += 1
    
    # Test 27: Center of Mass Calculation
    try:
        import Part
        # Symmetric box - COM should be at geometric center
        box = Part.makeBox(20, 20, 20)
        com = box.CenterOfMass
        com_ok = abs(com.x - 10) < 0.01 and abs(com.y - 10) < 0.01 and abs(com.z - 10) < 0.01
        tests.append({'name': '27. Center of Mass', 'passed': com_ok,
                     'details': f'COM: ({com.x:.1f}, {com.y:.1f}, {com.z:.1f})',
                     'category': 'Transform'})
        passed += 1 if com_ok else 0
        failed += 0 if com_ok else 1
    except Exception as e:
        tests.append({'name': '27. Center of Mass', 'passed': False, 'error': str(e), 'category': 'Transform'})
        failed += 1
    
    # Test 28: Compound Shape Creation
    try:
        import Part
        box1 = Part.makeBox(10, 10, 10)
        box2 = Part.makeBox(10, 10, 10, App.Vector(20, 0, 0))
        sphere = Part.makeSphere(5, App.Vector(10, 10, 10))
        compound = Part.Compound([box1, box2, sphere])
        is_compound = compound.ShapeType == 'Compound'
        has_solids = len(compound.Solids) == 3
        compound_ok = is_compound and has_solids
        tests.append({'name': '28. Compound Creation', 'passed': compound_ok,
                     'details': f'Solids in compound: {len(compound.Solids)}',
                     'category': 'Transform'})
        passed += 1 if compound_ok else 0
        failed += 0 if compound_ok else 1
    except Exception as e:
        tests.append({'name': '28. Compound Creation', 'passed': False, 'error': str(e), 'category': 'Transform'})
        failed += 1
    
    # ========================================================================
    # CATEGORY 5: INFRASTRUCTURE & MONITORING TESTS (29-32)
    # ========================================================================
    
    # Test 29: AI I/O Directory Structure
    try:
        dirs_ok = os.path.exists(AI_IO_DIR) and os.path.exists(LEARNING_DIR)
        tests.append({'name': '29. AI Directories', 'passed': dirs_ok,
                     'io_dir': AI_IO_DIR, 'learn_dir': LEARNING_DIR,
                     'category': 'Infrastructure'})
        passed += 1 if dirs_ok else 0
        failed += 0 if dirs_ok else 1
    except Exception as e:
        tests.append({'name': '29. AI Directories', 'passed': False, 'error': str(e), 'category': 'Infrastructure'})
        failed += 1
    
    # Test 30: Monitor Timer Active
    try:
        timer_ok = _ai_monitor_timer and _ai_monitor_timer.isActive()
        tests.append({'name': '30. Command Monitor Timer', 'passed': True, 'active': timer_ok,
                     'category': 'Infrastructure'})
        passed += 1
    except Exception as e:
        tests.append({'name': '30. Command Monitor Timer', 'passed': False, 'error': str(e), 'category': 'Infrastructure'})
        failed += 1
    
    # Test 31: Health Check File
    try:
        health_ok = os.path.exists(HEALTH_CHECK_FILE)
        tests.append({'name': '31. Health Check File', 'passed': True, 'exists': health_ok,
                     'category': 'Infrastructure'})
        passed += 1
    except Exception as e:
        tests.append({'name': '31. Health Check File', 'passed': False, 'error': str(e), 'category': 'Infrastructure'})
        failed += 1
    
    # Test 32: Command Executor Instance
    try:
        exec_ok = _executor is not None and hasattr(_executor, 'execute_with_timeout')
        tests.append({'name': '32. Command Executor', 'passed': exec_ok,
                     'category': 'Infrastructure'})
        passed += 1 if exec_ok else 0
        failed += 0 if exec_ok else 1
    except Exception as e:
        tests.append({'name': '32. Command Executor', 'passed': False, 'error': str(e), 'category': 'Infrastructure'})
        failed += 1
    
    # ========================================================================
    # PRINT DETAILED SUMMARY
    # ========================================================================
    App.Console.PrintMessage("\n" + "="*80 + "\n")
    App.Console.PrintMessage(f"    AI BRIDGE v{Config.VERSION} - ADVANCED SYSTEM TEST RESULTS\n")
    App.Console.PrintMessage("    Tests derived from Technical_Data knowledge resources\n")
    App.Console.PrintMessage("="*80 + "\n")
    
    # Group by category
    categories = {}
    for t in tests:
        cat = t.get('category', 'Other')
        if cat not in categories:
            categories[cat] = {'passed': 0, 'failed': 0}
        if t['passed']:
            categories[cat]['passed'] += 1
        else:
            categories[cat]['failed'] += 1
    
    App.Console.PrintMessage("\nRESULTS BY CATEGORY:\n")
    App.Console.PrintMessage("-" * 50 + "\n")
    for cat, counts in categories.items():
        total = counts['passed'] + counts['failed']
        status = "✅" if counts['failed'] == 0 else "⚠️"
        App.Console.PrintMessage(f"  {status} {cat}: {counts['passed']}/{total} passed\n")
    
    App.Console.PrintMessage("\n" + "-" * 50 + "\n")
    App.Console.PrintMessage(f"📈 TOTAL: {passed}/{passed + failed} tests passed")
    if failed == 0:
        App.Console.PrintMessage(" ✅ ALL SYSTEMS OPERATIONAL\n")
    else:
        App.Console.PrintMessage(f" ⚠️ {failed} test(s) need attention\n")
    
    # Print any failures
    if failed > 0:
        App.Console.PrintMessage("\n❌ FAILED TESTS:\n")
        for t in tests:
            if not t['passed']:
                App.Console.PrintMessage(f"  • {t['name']}: {t.get('error', 'Check details')}\n")
    
    App.Console.PrintMessage("="*80 + "\n\n")
    
    return {
        'tests': tests,
        'passed': passed,
        'failed': failed,
        'total': passed + failed
    }

# ============================================================
# COMMAND PROCESSOR WITH RECOVERY - CRITICAL FIX
# ============================================================

def process_ai_commands_with_recovery():
    """Wrapper with automatic recovery from crashes.

    CRITICAL FIX: Timer now automatically recovers from crashes
    CRITICAL FIX 2: Prevent recursive timer callbacks
    CRITICAL FIX 3: Block during command execution
    v3.4.7: nothing escapes this slot, and the error path no longer depends
    on App.Console still being FreeCAD's.
    """
    global _in_timer_callback, _executing_command

    # Stamp liveness before anything can return or raise. This is the only
    # evidence the watchdog thread has that the GUI event loop is still
    # delivering timer events at all.
    _tick('monitor')

    # CRITICAL: If executing a command, skip ALL timer callbacks
    if _executing_command:
        return

    # v4.0.05: paused is connected but not accepting work. The liveness
    # tick above has already happened, so the watchdog does not mistake a
    # pause for dead timers.
    if _paused:
        return

    # Prevent recursive calls from timer
    if _in_timer_callback:
        return

    _in_timer_callback = True
    try:
        process_ai_commands()
        # v4.0.07: write the results NOW, not in up to five seconds.
        # Replies were appended to _result_buffer and left for a 5000 ms
        # timer, so a command finishing in 20 ms still answered in up to
        # five seconds -- measured twice at exactly 5.0 s. flush_result_
        # buffer() takes its own lock and returns at once on an empty
        # buffer, so calling it every cycle is cheap. The timer stays as
        # the backstop for anything appended outside a poll.
        flush_result_buffer()
        _state.reset_consecutive_errors()

    except BaseException as e:
        # Every step of the error path is independently guarded and logs
        # through the captured console. The old version reported the failure
        # with App.Console.PrintError, and if that call itself raised - a
        # patched console - the exception escaped this slot and the Bridge
        # stopped processing commands for good, with a status file that still
        # said monitoring_active: true.
        try:
            _state.increment_errors()
            consecutive = _state.consecutive_errors
        except BaseException:
            consecutive = 0

        _log_err(f"Command processor error #{consecutive}: {e}\n")

        try:
            log_error_with_context(e, None, "command_processor_crash", None)
        except BaseException:
            pass

        update_status({
            'error_state': True,
            'consecutive_errors': consecutive,
            'last_error': str(e)
        })

        # Automatic recovery
        if consecutive >= Config.MAX_CONSECUTIVE_ERRORS:
            _log_err(f"Max errors reached "
                     f"({Config.MAX_CONSECUTIVE_ERRORS}) - restarting "
                     f"monitoring\n")

            def restart():
                try:
                    stop_ai_monitoring()
                    start_ai_monitoring()
                except BaseException as exc:
                    _log_err(f"Monitoring restart failed: {exc}\n")

            try:
                QtCore.QTimer.singleShot(Config.RESTART_COOLDOWN_MS, restart)
            except BaseException:
                pass
    finally:
        _in_timer_callback = False

# ============================================================
# REPORT & SELECTION CAPTURE
# ============================================================

class _ConsoleCapture:
    """Captures App.Console messages in real-time during command execution.

    FreeCAD's Report View is driven by App.Console.Print* calls. This class
    intercepts those messages so they can be returned to AI agents in the
    result JSON — no more asking the user to paste the Report View.

    Usage:
        _console_capture.start()   # before exec()
        ... exec() ...
        messages = _console_capture.stop()  # after exec()
    """

    def __init__(self):
        self._messages = []
        self._warnings = []
        self._errors = []
        self._capturing = False
        self._observer = None
        self._unavailable = None

    def start(self):
        """Begin capturing console output."""
        self._messages = []
        self._warnings = []
        self._errors = []
        self._capturing = True
        self._unavailable = None
        # Try to install a console observer.
        try:
            observer = _ConsoleObserver(self)
            App.Console.AddObserver(observer)
            self._observer = observer
        except Exception as e:
            # v3.4.6: App.Console.AddObserver does NOT exist on FreeCAD 1.1
            # or 26.3 - verified, dir(App.Console) exposes GetObservers and
            # no AddObserver on both. So this branch has always been taken
            # on current builds and stop() has always returned empty lists:
            # every report_view this bridge has ever sent back was silently
            # empty. Record the reason so the client is told the capture is
            # unavailable, instead of reading emptiness as "no output".
            self._observer = None
            self._unavailable = f"{type(e).__name__}: {e}"

    def stop(self):
        """Stop capturing and return captured messages."""
        self._capturing = False
        if self._observer:
            try:
                App.Console.RemoveObserver(self._observer)
            except Exception:
                pass
            self._observer = None
        captured = {
            'messages': self._messages[-50:],  # Last 50 messages
            'warnings': self._warnings[-20:],
            'errors': self._errors[-20:]
        }
        # v3.4.6: say so rather than returning a silently empty capture.
        if self._unavailable:
            captured['capture_unavailable'] = self._unavailable
        return captured

    def add_message(self, text):
        if self._capturing and text.strip():
            self._messages.append(text.strip())

    def add_warning(self, text):
        if self._capturing and text.strip():
            self._warnings.append(text.strip())

    def add_error(self, text):
        if self._capturing and text.strip():
            self._errors.append(text.strip())


class _ConsoleObserver:
    """FreeCAD Console Observer that feeds captured text to _ConsoleCapture."""

    def __init__(self, capture):
        self._capture = capture

    def Message(self, text):
        self._capture.add_message(text)

    def Warning(self, text):
        self._capture.add_warning(text)

    def Error(self, text):
        self._capture.add_error(text)

    def Log(self, text):
        pass  # Skip verbose log messages


_console_capture = _ConsoleCapture()


def capture_report_view_state():
    """Return captured Report View messages from the last command execution.

    This now uses _console_capture (real-time observer) instead of reading
    non-existent FreeCAD*.log files. Call _console_capture.start() before
    exec() and _console_capture.stop() after exec() — this function then
    formats whatever was captured.
    """
    try:
        messages = []

        # Get real-time captured console messages (populated by _console_capture)
        # These are already collected during exec() via the observer
        captured = _console_capture.stop() if _console_capture._capturing else {
            'messages': _console_capture._messages[-50:],
            'warnings': _console_capture._warnings[-20:],
            'errors': _console_capture._errors[-20:]
        }

        for msg in captured.get('messages', []):
            messages.append(f"[MSG] {msg}")
        for warn in captured.get('warnings', []):
            messages.append(f"[WARN] {warn}")
        for err in captured.get('errors', []):
            messages.append(f"[ERR] {err}")

        # Also check document object errors
        if App.ActiveDocument:
            for obj in App.ActiveDocument.Objects:
                if hasattr(obj, 'State'):
                    if 'Invalid' in str(obj.State) or 'Error' in str(obj.State):
                        messages.append(f"[OBJ] {obj.Label}: {obj.State}")

        return {
            'timestamp': datetime.now().isoformat(),
            'message_count': len(messages),
            'messages': messages
        }

    except Exception as e:
        return {
            'timestamp': datetime.now().isoformat(),
            'message_count': 0,
            'messages': [],
            'error': str(e)
        }

def capture_notification_state():
    """Capture FreeCAD notifications and status bar messages"""
    try:
        notifications = []
        
        # Try to capture from main window status bar
        try:
            mw = Gui.getMainWindow()
            if mw and hasattr(mw, 'statusBar'):
                status_bar = mw.statusBar()
                if status_bar:
                    status_text = status_bar.currentMessage()
                    if status_text:
                        notifications.append({
                            'type': 'statusbar',
                            'message': status_text
                        })
        except Exception as e:
            pass
        
        # Check for active document warnings/errors
        if App.ActiveDocument:
            # Check recompute status
            if hasattr(App.ActiveDocument, 'RecomputesFrozen'):
                if App.ActiveDocument.RecomputesFrozen:
                    notifications.append({
                        'type': 'document_status',
                        'message': 'Document recomputes are frozen'
                    })
            
            # Check for objects with issues
            error_objects = []
            warning_objects = []
            for obj in App.ActiveDocument.Objects:
                if hasattr(obj, 'State'):
                    state_str = str(obj.State)
                    if 'Invalid' in state_str or 'Error' in state_str:
                        error_objects.append(obj.Label)
                    elif 'Touch' in state_str or 'Restore' in state_str:
                        warning_objects.append(obj.Label)
            
            if error_objects:
                notifications.append({
                    'type': 'object_errors',
                    'message': f"Objects with errors: {', '.join(error_objects[:5])}" + (f" (+{len(error_objects)-5} more)" if len(error_objects) > 5 else "")
                })
            
            if warning_objects:
                notifications.append({
                    'type': 'object_warnings',
                    'message': f"Objects need recompute: {', '.join(warning_objects[:5])}" + (f" (+{len(warning_objects)-5} more)" if len(warning_objects) > 5 else "")
                })
        
        return {
            'timestamp': datetime.now().isoformat(),
            'notification_count': len(notifications),
            'notifications': notifications
        }
    
    except Exception as e:
        return {
            'timestamp': datetime.now().isoformat(),
            'notification_count': 0,
            'notifications': [],
            'error': str(e)
        }

def capture_selection_state():
    """Capture current selection state"""
    try:
        selection = Gui.Selection.getSelection()
        selection_ex = Gui.Selection.getSelectionEx()
        
        selection_data = {
            'timestamp': datetime.now().isoformat(),
            'object_count': len(selection),
            'objects': []
        }
        
        for obj in selection:
            obj_info = {
                'label': obj.Label,
                'type': obj.TypeId,
                'name': obj.Name,
                'visible': obj.ViewObject.Visibility if hasattr(obj, 'ViewObject') else None
            }
            selection_data['objects'].append(obj_info)
        
        selection_data['detailed'] = []
        for sel_ex in selection_ex:
            detail = {
                'object': sel_ex.Object.Label if sel_ex.Object else None,
                'sub_element_names': sel_ex.SubElementNames,
                'has_sub_objects': len(sel_ex.SubObjects) > 0
            }
            selection_data['detailed'].append(detail)
        
        return selection_data
    
    except Exception as e:
        return {
            'timestamp': datetime.now().isoformat(),
            'object_count': 0,
            'objects': [],
            'error': str(e)
        }

# ============================================================
# MONITORING CONTROL
# ============================================================

def setup_ai_io_directory():
    """Create AI I/O directory structure with validation"""
    try:
        # Validate and create directories
        for directory in [AI_IO_DIR, LEARNING_DIR]:
            # Ensure directory is safe
            abs_dir = os.path.abspath(directory)
            os.makedirs(abs_dir, exist_ok=True)
        
        # Create initial files
        for filepath in [AI_INPUT_FILE, AI_OUTPUT_FILE, AI_REPORT_FILE, AI_SELECTION_FILE]:
            if not os.path.exists(filepath):
                with open(filepath, 'w') as f:
                    pass
        
        # Create initial status
        update_status({
            'initialized': datetime.now().isoformat(),
            'monitoring_active': False,
            'freecad_version': f"{App.Version()[0]}.{App.Version()[1]}",
            'ai_bridge_version': Config.VERSION,
            # v5.0.17: update_status MERGES into the existing file, so keys
            # written by a dead previous session (watchdog liveness, stall
            # length, error state) otherwise survive a restart and contradict
            # the fresh heartbeat. Seen live: a restarted 5.0.16 still read
            # "liveness": "timers_dead" / "stalled_seconds": 21.1 from the
            # run it had just replaced.
            'liveness': 'starting',
            'stalled_seconds': 0,
            'error_state': False,
            'last_error': None
        })
        
        return True
    
    except Exception as e:
        App.Console.PrintError(f"Cannot setup I/O directory: {e}\n")
        return False

# ============================================================
# AI CONTEXT SUMMARY GENERATOR
# ============================================================

def generate_ai_context_summary():
    """
    Generate comprehensive AI context summary on startup
    Provides AI assistants with instant understanding of available patterns and resources
    """
    try:
        context_file = os.path.join(AI_IO_DIR, "ai_context_summary.txt")
        tech_data_path = library_dir()
        kb_file = os.path.join(tech_data_path, "FreeCAD_Knowledge_Base.json")
        
        with open(context_file, 'w', encoding='utf-8') as f:
            f.write("="*70 + "\n")
            f.write("AI ASSISTANT CONTEXT SUMMARY - AUTO-GENERATED ON STARTUP\n")
            f.write("="*70 + "\n\n")
            f.write(f"Generated: {datetime.now().strftime('%Y-%m-%d %H:%M:%S')}\n\n")

            # === CRITICAL PYTHON RULES (MUST READ FIRST) ===
            f.write("="*70 + "\n")
            f.write("CRITICAL PYTHON EXECUTION RULES (READ BEFORE SENDING ANY COMMANDS)\n")
            f.write("="*70 + "\n")
            f.write("Each command runs in a FRESH exec() scope. Variables DO NOT persist.\n")
            f.write("EVERY command MUST re-declare variables it needs.\n\n")
            f.write("MANDATORY TEMPLATE FOR EVERY COMMAND:\n")
            f.write("-"*70 + "\n")
            f.write("  doc = App.ActiveDocument          # REQUIRED in every command\n")
            f.write("  import Part                        # if using Part module\n")
            f.write("  import math                        # if using math functions\n")
            f.write("  # ... your code ...\n")
            f.write("  doc.recompute()\n\n")
            f.write("COMMON ERRORS TO AVOID:\n")
            f.write("-"*70 + "\n")
            f.write("  NameError 'doc' not defined  -> Add doc = App.ActiveDocument\n")
            f.write("  SyntaxError with for/if      -> Use real newlines (\\n), not semicolons\n")
            f.write("  f-string backslash error     -> No \\ inside f-string {expressions}\n")
            f.write("  Security: import os blocked  -> Only use allowed modules (see below)\n\n")
            f.write("ALLOWED MODULES (pre-loaded in exec scope):\n")
            f.write("  App, Gui, FreeCAD, FreeCADGui, Part, Draft, Sketcher, Mesh, math\n")
            f.write("ALLOWED IMPORTS:\n")
            f.write("  datetime, PartDesign, Arch, TechDraw, Path, Spreadsheet\n")
            f.write("BLOCKED: os, sys, subprocess, open(), eval(), exec()\n")
            f.write("AVAILABLE since v5.0.18: exception classes (except Exception: works),\n")
            f.write("  repr, map, filter, iter, next, format, class definitions.\n\n")
            f.write("BEST PRACTICE: Send ONE large command with all objects rather than\n")
            f.write("many small commands that each need doc = App.ActiveDocument.\n\n")
            f.write("FULL RULES: " + os.path.join(tech_data_path, "AI_Bridge_Python_Rules.txt") + "\n\n")

            # === AGENT API (v5.0.17) ===
            f.write("="*70 + "\n")
            f.write("AGENT API - PARAMETRIC MEMORY & MULTICORE (AIBridge / App.AIBridge)\n")
            f.write("="*70 + "\n")
            f.write("AIBridge is pre-loaded in the exec scope; run_macro files reach the\n")
            f.write("same object as App.AIBridge. Named verbs, no code strings.\n\n")
            f.write("MEMORY - a document's memory travels WITH it (log folder beside the\n")
            f.write(".FCStd, embedded copy inside it):\n")
            f.write("  AIBridge.memory_recall()      -> what this document already knows\n")
            f.write("  AIBridge.memory_start()       -> begin logging (save the doc first)\n")
            f.write("  AIBridge.memory_note('text')  -> record a decision in the log\n")
            f.write("  AIBridge.memory_checkpoint()  -> flush + re-embed into the .FCStd\n")
            f.write("  AIBridge.memory_stop()        -> embed and stop\n")
            f.write("  AIBridge.inventory()          -> measured summary of the model\n\n")
            f.write("MULTICORE - heavy work runs in a SECOND FreeCAD process:\n")
            f.write("  job = AIBridge.capture()      -> whole+section images, headless worker\n")
            f.write("  AIBridge.capture_status(job)  -> manifest when the worker is done\n")
            f.write("  AIBridge.outsource()          -> mesh-tool targets; push/pull/launch\n\n")
            f.write("Call print(AIBridge.help()) for the one-screen verb list.\n\n")

            # === KNOWLEDGE BASE REVIEW ===
            f.write("="*70 + "\n")
            f.write("KNOWLEDGE BASE REVIEW (FreeCAD_Knowledge_Base.json)\n")
            f.write("="*70 + "\n")
            if os.path.exists(kb_file):
                with open(kb_file, 'r', encoding='utf-8') as kb:
                    kb_data = json.load(kb)
                    metadata = kb_data.get('metadata', {})
                    f.write(f"Version: {metadata.get('version', 'N/A')}\n")
                    f.write(f"Total Patterns: {metadata.get('total_patterns', 0)}\n")
                    f.write(f"FreeCAD Version: {metadata.get('freecad_version', 'N/A')}\n")
                    f.write(f"API Coverage: {metadata.get('api_coverage', 'N/A')}\n\n")
                    
                    # Quick reference commands
                    f.write("QUICK REFERENCE COMMANDS:\n")
                    f.write("-" * 70 + "\n")
                    doc_ops = kb_data.get('quick_reference', {}).get('document_operations', {})
                    f.write("Documents:\n")
                    for key, cmd in doc_ops.items():
                        f.write(f"  {key}: {cmd}\n")
                    f.write("\n")
                    
                    # Basic objects
                    basic = kb_data.get('quick_reference', {}).get('basic_objects', {})
                    f.write("Basic Objects:\n")
                    for obj_type, info in list(basic.items())[:5]:
                        f.write(f"  {obj_type}: {info.get('create', 'N/A')}\n")
                    f.write("\n")
                    
                    # GUI operations
                    gui = kb_data.get('gui_operations', {})
                    if 'selection' in gui:
                        f.write("GUI Selection:\n")
                        sel = gui['selection']
                        for key, cmd in list(sel.items())[:5]:
                            if isinstance(cmd, str):
                                f.write(f"  {key}: {cmd}\n")
                    f.write("\n")
                    
                    # Common patterns
                    patterns = kb_data.get('common_patterns', {})
                    if patterns:
                        f.write("Common Patterns Available:\n")
                        for key in patterns.keys():
                            f.write(f"  - {key}\n")
                    f.write("\n")
            else:
                f.write("[WARNING] Knowledge Base file not found\n\n")
            
            # === LEARNING DATABASE REVIEW ===
            f.write("="*70 + "\n")
            f.write("LEARNING DATABASE REVIEW (AI_Learning_Database.json)\n")
            f.write("="*70 + "\n")
            if os.path.exists(LEARNING_DB_FILE):
                with open(LEARNING_DB_FILE, 'r', encoding='utf-8') as db:
                    learning_data = json.load(db)
                    f.write(f"Total Successful Patterns: {learning_data['metadata']['total_patterns']}\n")
                    f.write(f"Last Updated: {learning_data['metadata']['last_updated']}\n\n")
                    
                    # Recent successful commands
                    f.write("RECENT SUCCESSFUL COMMANDS (Last 10):\n")
                    f.write("-" * 70 + "\n")
                    # v3.4.0 PROVENANCE GATE: only VERIFIED patterns are surfaced to
                    # connecting agents. Unreviewed local-model output must never be
                    # presented to Claude (or anyone else) as established practice.
                    _verified_patterns = [
                        p for p in learning_data.get('successful_patterns', [])
                        if p.get('verified', True)
                    ]
                    _unverified_count = (len(learning_data.get('successful_patterns', []))
                                         - len(_verified_patterns))
                    if _unverified_count:
                        f.write(f"({_unverified_count} unverified pattern(s) withheld "
                                f"pending human review)\n")
                    recent = _verified_patterns[-10:] if _verified_patterns else []
                    for i, pattern in enumerate(recent, 1):
                        cmd = pattern['command']
                        if len(cmd) > 100:
                            cmd = cmd[:100] + "..."
                        f.write(f"{i}. [{pattern['timestamp'][:19]}] {cmd}\n")
                    f.write("\n")
                    
                    # Command statistics
                    f.write("COMMAND CATEGORIES:\n")
                    f.write("-" * 70 + "\n")
                    categories = {}
                    for pattern in learning_data['successful_patterns']:
                        cmd = pattern['command']
                        if 'newDocument' in cmd or 'ActiveDocument' in cmd:
                            categories['Document Operations'] = categories.get('Document Operations', 0) + 1
                        elif 'addObject' in cmd:
                            categories['Object Creation'] = categories.get('Object Creation', 0) + 1
                        elif 'Selection' in cmd:
                            categories['GUI/Selection'] = categories.get('GUI/Selection', 0) + 1
                        elif 'Part.' in cmd:
                            categories['Part Scripting'] = categories.get('Part Scripting', 0) + 1
                        else:
                            categories['Other'] = categories.get('Other', 0) + 1
                    
                    for cat, count in categories.items():
                        f.write(f"  {cat}: {count} patterns\n")
                    f.write("\n")
                    # LEARNING: surface mistakes-to-avoid and proven templates to the AI
                    _mistakes = learning_data.get("common_mistakes", [])
                    if _mistakes:
                        f.write("COMMON MISTAKES TO AVOID (learned):\n")
                        f.write("-" * 70 + "\n")
                        for _m in _mistakes[-10:]:
                            f.write("  X " + str(_m.get("mistake", "")) + "\n")
                            if _m.get("correct_approach"):
                                f.write("    -> " + str(_m.get("correct_approach"))[:100] + "\n")
                        f.write("\n")
                    _templates = learning_data.get("command_templates", {})
                    if _templates:
                        f.write("PROVEN COMMAND TEMPLATES (auto-promoted):\n")
                        f.write("-" * 70 + "\n")
                        for _tn, _t in list(_templates.items())[:10]:
                            f.write("  [" + str(_tn) + "] " + str(_t.get("description", "")) + " (used " + str(_t.get("usage_count", 0)) + "x)\n")
                        f.write("\n")
            else:
                f.write("[INFO] Learning Database not yet created - will populate as commands succeed\n\n")
            
            # === WORKBENCH DATABASE REVIEW ===
            f.write("="*70 + "\n")
            f.write("WORKBENCH DATABASE REVIEW\n")
            f.write("="*70 + "\n")
            wb_kb_file = os.path.join(tech_data_path, "FreeCAD_Workbenches_Knowledge_Base.json")
            if os.path.exists(wb_kb_file):
                with open(wb_kb_file, 'r', encoding='utf-8') as wbf:
                    wb_data = json.load(wbf)
                    wb_meta = wb_data.get('metadata', {})
                    f.write(f"Total Workbenches: {wb_meta.get('total_workbenches', 0)}\n")
                    f.write(f"Categories: {len(wb_meta.get('categories', []))}\n")
                    f.write(f"Core Workbenches: {len(wb_data.get('core_workbenches', {}))}\n\n")
                    
                    # List core workbenches
                    f.write("CORE WORKBENCHES:\n")
                    f.write("-" * 70 + "\n")
                    for wb_name, wb_info in wb_data.get('core_workbenches', {}).items():
                        desc = wb_info.get('description', '')[:60]
                        f.write(f"  • {wb_name}: {desc}\n")
                    f.write("\n")
                    
                    # List external categories
                    f.write("EXTERNAL WORKBENCH CATEGORIES:\n")
                    f.write("-" * 70 + "\n")
                    for category in wb_meta.get('categories', []):
                        f.write(f"  • {category}\n")
                    f.write("\n")
                    
                    # Popular workbenches
                    f.write("POPULAR EXTERNAL WORKBENCHES:\n")
                    f.write("-" * 70 + "\n")
                    popular = ['A2plus', 'Assembly4', 'Fasteners', 'SheetMetal', 'Curves', 
                               'Render', 'CfdOF', 'KicadStepUp', 'Gear', 'ModernUI']
                    for wb_name in popular:
                        for category, workbenches in wb_data.get('external_workbenches', {}).items():
                            if isinstance(workbenches, list):
                                for wb in workbenches:
                                    if wb.get('name') == wb_name:
                                        f.write(f"  • {wb_name} ({category.replace('_', ' ').title()}): ")
                                        f.write(f"{wb.get('description', '')[:50]}...\n")
                                        break
                    f.write("\n")
                    
                    # Query helper available
                    f.write("WORKBENCH QUERY HELPER:\n")
                    f.write("-" * 70 + "\n")
                    f.write("Natural language queries available via:\n")
                    f.write("  sys.path.append(r'%s')\n"
                            % library_dir())
                    f.write("  from Workbench_Query_Helper import query_workbenches\n")
                    f.write("  result = query_workbenches('assembly')\n\n")
            else:
                f.write("[INFO] Workbench database not found\n\n")
            
            # === PYTHON DATABASE REVIEW ===
            f.write("="*70 + "\n")
            f.write("PYTHON KNOWLEDGE DATABASE REVIEW\n")
            f.write("="*70 + "\n")
            py_kb_file = os.path.join(tech_data_path, "Python_Standard_Library_Knowledge_Base.json")
            if os.path.exists(py_kb_file):
                with open(py_kb_file, 'r', encoding='utf-8') as pyf:
                    py_data = json.load(pyf)
                    py_meta = py_data.get('metadata', {})
                    f.write(f"Total Modules: {py_meta.get('total_modules', 0)}\n")
                    f.write(f"Total Patterns: {py_meta.get('total_patterns', 0)}\n")
                    f.write(f"Python Version: {py_meta.get('python_version', 'N/A')}\n\n")
                    
                    # List essential modules
                    f.write("ESSENTIAL PYTHON MODULES:\n")
                    f.write("-" * 70 + "\n")
                    modules = list(py_data.get('essential_modules', {}).keys())[:15]
                    f.write(f"  {', '.join(modules)}\n")
                    f.write(f"  ... and {py_meta.get('total_modules', 0) - 15} more\n\n")
                    
                    # Pattern categories
                    f.write("PYTHON PATTERN CATEGORIES:\n")
                    f.write("-" * 70 + "\n")
                    for pattern_cat in py_data.get('python_patterns', {}).keys():
                        f.write(f"  • {pattern_cat.replace('_', ' ').title()}\n")
                    f.write("\n")
                    
                    # Query helper
                    f.write("PYTHON QUERY HELPER:\n")
                    f.write("-" * 70 + "\n")
                    f.write("Natural language Python queries available via:\n")
                    f.write("  sys.path.append(r'%s')\n"
                            % library_dir())
                    f.write("  from Python_Query_Helper import query_python\n")
                    f.write("  result = query_python('How do I read a JSON file?')\n\n")
            else:
                f.write("[INFO] Python knowledge database not found\n\n")
            
            # === REFERENCE FILES ===
            f.write("="*70 + "\n")
            f.write("REFERENCE FILES (For Deep Dive)\n")
            f.write("="*70 + "\n")
            f.write("1. Knowledge Base (PRIMARY - Machine Readable):\n")
            f.write(f"   {kb_file}\n")
            f.write("   - 250+ patterns in JSON format for fast lookup\n\n")
            f.write("2. Workbench Database (NEW - Comprehensive):\n")
            f.write(f"   {wb_kb_file}\n")
            f.write("   - 120+ workbenches (core + external)\n")
            f.write("   - Installation instructions\n")
            f.write("   - API patterns and workflows\n\n")
            f.write("3. Learning Database (Auto-Updated):\n")
            f.write(f"   {LEARNING_DB_FILE}\n")
            f.write("   - All successful commands with timestamps\n\n")
            # v5.0.14: the folder once, from library_dir(), then bare
            # filenames. Eight absolute paths typed into the source named
            # one person's Desktop and were wrong on every other machine.
            f.write("4-9. Reference documents, all in:\n")
            f.write("   %s\n\n" % library_dir())
            for _name, _what in (
                    ("README.txt",
                     "QDockWidget patterns, PySide compatibility, "
                     "34-point checklist"),
                    ("INDEX.txt",
                     "production macros, steel profiles, parametric tools"),
                    ("Expressions_Reference.txt",
                     "parametric design, units, conditionals, "
                     "vector/matrix functions"),
                    ("Python_Scripting_Conventions.txt",
                     "PEP8, imports, function patterns, best practices"),
                    ("Part_Scripting_Reference.txt",
                     "shapes, geometry, booleans, transformations"),
                    ("Parametric_Objects_Reference.txt",
                     "parametric objects, properties, execute method"),
                    ("GUI_Creation_Reference.txt",
                     "Qt/PySide, task panels, dialogs, user input")):
                f.write("   %-36s %s\n" % (_name, _what))
            f.write("\n")
            
            # === HOW TO SEND COMMANDS (from CLAUDE.md - universal for all AIs) ===
            f.write("="*70 + "\n")
            f.write("HOW TO SEND COMMANDS TO FREECAD\n")
            f.write("="*70 + "\n")
            f.write("You are connected to FreeCAD via the AI Bridge file-based protocol.\n")
            f.write("FreeCAD is running separately and monitors the input file.\n\n")
            f.write("METHOD 1 - Helper script (if available in workspace):\n")
            f.write("-"*70 + "\n")
            f.write("  python send_to_freecad.py \"YOUR_PYTHON_COMMAND\" \"Description\"\n")
            f.write("  python send_to_freecad.py --read          # Read latest result\n")
            f.write("  python send_to_freecad.py --results 5     # Last 5 results\n")
            f.write("  python send_to_freecad.py --status        # Check bridge alive\n\n")
            f.write("METHOD 2 - Write directly to JSONL input file:\n")
            f.write("-"*70 + "\n")
            f.write(f"  Input:  {AI_INPUT_FILE}\n")
            f.write(f"  Output: {AI_OUTPUT_FILE}\n")
            f.write(f"  Status: {AI_STATUS_FILE}\n")
            f.write("  Format: one JSON object per line with 'id', 'code', 'timestamp' fields\n\n")
            f.write("Multi-line commands (use \\n for newlines):\n")
            f.write("  python send_to_freecad.py \"import Part\\nbox = Part.makeBox(50,30,10)\\n")
            f.write("App.ActiveDocument.addObject('Part::Feature','Base').Shape = box\"\n\n")

            # === WORKFLOW RULES ===
            f.write("="*70 + "\n")
            f.write("WORKFLOW RULES (CRITICAL)\n")
            f.write("="*70 + "\n")
            f.write("1. Send ONE command at a time - wait for result before sending next\n")
            f.write("2. Always check results - run --read after each command\n")
            f.write("3. Do NOT summarize after successful commands - keep responses brief\n")
            f.write("4. If a command fails, read the error and fix it - don't spam variations\n")
            f.write("5. Always call App.ActiveDocument.recompute() after geometry changes\n")
            f.write("6. Check App.ActiveDocument exists before operations\n")
            f.write("7. No special characters in commands (no degree/micro/plus-minus symbols)\n")
            f.write("8. Use math.radians(45) not 45deg\n\n")

            # === AI INSTRUCTIONS ===
            f.write("="*70 + "\n")
            f.write("AI ASSISTANT INSTRUCTIONS\n")
            f.write("="*70 + "\n")
            f.write("PRIORITY: Always reference the Knowledge Base JSON first for patterns!\n\n")
            f.write("WORKFLOW:\n")
            f.write("1. Read this context summary and the Python Rules file FIRST\n")
            f.write("2. Check Knowledge Base for exact pattern match\n")
            f.write("3. Check Learning Database for recent successful examples\n")
            f.write("4. Combine patterns from both sources\n")
            f.write("5. Test command format before sending\n\n")

            f.write("KEY PATTERNS FROM KNOWLEDGE BASE:\n")
            f.write("-" * 70 + "\n")
            f.write("REMEMBER: Every command needs doc = App.ActiveDocument at the start!\n\n")
            f.write("  # Document management\n")
            f.write("  App.newDocument('Name')\n")
            f.write("  App.ActiveDocument.recompute()\n")
            f.write("  App.ActiveDocument.saveAs('/path/to/file.FCStd')\n\n")
            f.write("  # Primitives (always set doc = App.ActiveDocument first)\n")
            f.write("  doc = App.ActiveDocument\n")
            f.write("  doc.addObject('Part::Box', 'MyBox')     # then set .Length/.Width/.Height\n")
            f.write("  doc.addObject('Part::Cylinder', 'MyCyl') # then set .Radius/.Height\n")
            f.write("  doc.addObject('Part::Sphere', 'MySphere') # then set .Radius\n\n")
            f.write("  # Part module shapes\n")
            f.write("  doc = App.ActiveDocument\n")
            f.write("  import Part\n")
            f.write("  box = Part.makeBox(L, W, H)\n")
            f.write("  cyl = Part.makeCylinder(R, H)\n")
            f.write("  obj = doc.addObject('Part::Feature', 'Name')\n")
            f.write("  obj.Shape = shape\n\n")
            f.write("  # Boolean ops\n")
            f.write("  fuse = shape1.fuse(shape2)\n")
            f.write("  cut = shape1.cut(shape2)\n")
            f.write("  common = shape1.common(shape2)\n\n")
            f.write("  # Placement\n")
            f.write("  obj.Placement.Base = FreeCAD.Vector(x, y, z)\n")
            f.write("  obj.Placement.Rotation = FreeCAD.Rotation(FreeCAD.Vector(0,0,1), angle)\n\n")
            f.write("  # Boolean Cut via document objects\n")
            f.write("  cut = doc.addObject('Part::Cut', 'name')\n")
            f.write("  cut.Base = obj1; cut.Tool = obj2\n\n")
            f.write("  # Selection\n")
            f.write("  FreeCADGui.Selection.getSelection()\n\n")
            f.write("  # View\n")
            f.write("  Gui.SendMsgToActiveView('ViewFit')\n\n")

            f.write("AUTONOMY:\n")
            f.write("-" * 70 + "\n")
            f.write("You have FULL permission to:\n")
            f.write("  - Send any FreeCAD Python command via the bridge\n")
            f.write("  - Read and write files in the workspace\n")
            f.write("  - Execute terminal commands to interact with the bridge\n")
            f.write("  - Read knowledge bases to improve responses\n")
            f.write("  - Automatically correct failed commands based on error feedback\n\n")
            
            f.write("="*70 + "\n")
            f.write("END OF CONTEXT SUMMARY\n")
            f.write("="*70 + "\n")
        
        App.Console.PrintMessage(f"[AI] Context summary created: {context_file}\n")
        App.Console.PrintMessage("     AI assistants should review this file on startup!\n\n")
        return True
        
    except Exception as e:
        App.Console.PrintWarning(f"Could not create AI context summary: {e}\n")
        import traceback
        App.Console.PrintWarning(f"{traceback.format_exc()}\n")
        return False

def _watchdog_loop():
    """v3.3.3 GUI-freeze detector. Runs on a DAEMON thread.

    FreeCAD's API is not thread-safe, so Bridge commands must run on the GUI
    (main) thread - which means a long command freezes the whole app. This
    watchdog cannot interrupt that (a hard kill would corrupt the document), but
    it keeps running while the GUI is blocked (the GIL is released during OCCT
    calls and periodically during pure-Python loops), so it can DETECT and LOG
    the freeze instead of leaving a silent mystery. Philosophy (Rule 42): detect,
    warn, never block.

    IMPORTANT: this thread must NEVER touch the FreeCAD API (App/Gui/App.Console)
    - it only writes plain files, which is thread-safe.
    """
    watchdog_file = os.path.join(AI_IO_DIR, 'ai_watchdog.json')
    warn_sec = getattr(Config, 'WATCHDOG_WARN_SEC', 30)
    sample_sec = getattr(Config, 'WATCHDOG_SAMPLE_SEC', 2.0)
    dead_sec = getattr(Config, 'WATCHDOG_TIMER_DEAD_SEC', 20)
    timers_reported = False
    # v3.4.8: a second, later threshold. The 30s warning says "this is slow";
    # this one says "this is never coming back".
    stuck_sec = getattr(Config, 'WATCHDOG_COMMAND_STUCK_SEC', 90)
    stuck_reported = False
    exec_since = None
    warned = False
    while not _watchdog_stop_event.is_set():
        try:
            if _executing_command:
                if exec_since is None:
                    exec_since = time.time()
                    warned = False
                elapsed = time.time() - exec_since
                if elapsed >= stuck_sec and not stuck_reported:
                    # v3.4.8: past this point the latch is the problem, not
                    # the command. Say so in the file clients read, because
                    # process_ai_commands_with_recovery() is now returning
                    # immediately on every tick and nothing else will.
                    stuck_reported = True
                    stamp = datetime.now().isoformat()
                    smsg = ("[WATCHDOG] A command has held the execution "
                            "latch for %.0fs. Every command sent since then "
                            "has been ignored, and will go on being ignored: "
                            "the poll returns at once while the latch is set. "
                            "Restart the Bridge in FreeCAD. (If the FreeCAD "
                            "window is responsive and idle, the command is "
                            "not running - the latch is stuck.)" % elapsed)
                    try:
                        with open(ERROR_LOG_FILE, 'a', encoding='utf-8') as ef:
                            ef.write("%s  %s\n" % (stamp, smsg))
                    except:
                        pass
                    update_status({
                        'monitoring_active': False,
                        'liveness': 'command_stuck',
                        'error_state': True,
                        'last_error': smsg,
                        'stuck_seconds': round(elapsed, 1)})
                if elapsed >= warn_sec and not warned:
                    warned = True
                    _dump_all_stacks("command has held the GUI thread %.0fs"
                                     % elapsed)
                    stamp = datetime.now().isoformat()
                    msg = ("[WATCHDOG] A Bridge command has held the FreeCAD GUI "
                           "thread for %.0fs - the UI is likely frozen. Long ops "
                           "(heavy shadow renders, big booleans/recomputes) must be "
                           "chunked or deferred; see Rule 42." % elapsed)
                    try:
                        with open(ERROR_LOG_FILE, 'a', encoding='utf-8') as ef:
                            ef.write("%s  %s\n" % (stamp, msg))
                    except:
                        pass
                    try:
                        with open(watchdog_file, 'w', encoding='utf-8') as wf:
                            wf.write(json.dumps({
                                'blocked': True,
                                'blocked_seconds': round(elapsed, 1),
                                'since': datetime.fromtimestamp(exec_since).isoformat(),
                                'note': 'GUI thread blocked by a long command',
                                # v3.4.0: distinguishes "the local model is thinking" (off-thread,
                                # harmless) from "a command is holding the GUI thread"
                                # (a real freeze). Without this the two look identical
                                # in the log when they happen to overlap.
                                'ollama_generating': bool(_ollama_generating),
                                'ollama_note': ('A Ollama generation was in flight; it runs '
                                                'on a worker thread and is NOT the cause of '
                                                'this freeze.') if _ollama_generating else ''
                            }))
                    except:
                        pass
            else:
                if warned:
                    # command finished after we warned - record the recovery
                    try:
                        with open(watchdog_file, 'w', encoding='utf-8') as wf:
                            wf.write(json.dumps({
                                'blocked': False,
                                'recovered_at': datetime.now().isoformat()
                            }))
                    except:
                        pass
                if stuck_reported:
                    stuck_reported = False
                    update_status({'monitoring_active': True,
                                   'liveness': 'ok', 'stuck_seconds': 0})
                exec_since = None
                warned = False
        except:
            pass

        # ---- v3.4.7: dead-timer detection -------------------------------
        # The block above only notices a freeze while a command is in flight.
        # On 2026-11-07 this Bridge went silent with no command running: the
        # heartbeat stopped, monitoring_active stayed true, and nothing was
        # written anywhere. This thread is the only one still running in that
        # state, so it is the one that has to say so.
        try:
            if _state.monitoring_active:
                snap = _liveness_snapshot()
                last = snap.get('monitor')
                ref = last if last is not None else snap.get('started')
                if ref is not None:
                    stalled = time.monotonic() - ref
                    if stalled >= dead_sec and not timers_reported:
                        timers_reported = True
                        _dump_all_stacks("no command-poll tick for %.0fs"
                                         % stalled)
                        stamp = datetime.now().isoformat()
                        msg = ("[WATCHDOG] No command-poll tick for %.0fs. "
                               "The GUI event loop or the poll callback is "
                               "dead: this Bridge is NOT processing commands, "
                               "whatever ai_status.json said before this "
                               "line. Restart the Bridge in FreeCAD."
                               % stalled)
                        try:
                            with open(ERROR_LOG_FILE, 'a',
                                      encoding='utf-8') as ef:
                                ef.write("%s  %s\n" % (stamp, msg))
                        except:
                            pass
                        try:
                            with open(watchdog_file, 'w',
                                      encoding='utf-8') as wf:
                                wf.write(json.dumps({
                                    'blocked': True,
                                    'liveness': 'timers_dead',
                                    'stalled_seconds': round(stalled, 1),
                                    'note': msg}))
                        except:
                            pass
                        # Correct the lie in the status file itself, because
                        # that is the file every client reads first.
                        update_status({
                            'monitoring_active': False,
                            'liveness': 'timers_dead',
                            'error_state': True,
                            'last_error': msg,
                            'stalled_seconds': round(stalled, 1)})
                    elif stalled < dead_sec and timers_reported:
                        timers_reported = False
                        update_status({'monitoring_active': True,
                                       'liveness': 'ok'})
            # The watchdog's own pulse. A client comparing this against
            # last_heartbeat can tell "process alive, timers dead" from
            # "FreeCAD is gone" - two states that used to look identical.
            try:
                snap2 = _liveness_snapshot()
                now_m = time.monotonic()
                with open(os.path.join(AI_IO_DIR, 'ai_liveness.json'), 'w',
                          encoding='utf-8') as lf:
                    lf.write(json.dumps({
                        'watchdog_heartbeat': datetime.now().isoformat(),
                        'monitor_tick_age_s': (
                            None if snap2.get('monitor') is None
                            else round(now_m - snap2['monitor'], 1)),
                        'status_tick_age_s': (
                            None if snap2.get('status') is None
                            else round(now_m - snap2['status'], 1)),
                        'monitoring_active': bool(_state.monitoring_active),
                        'executing_command': bool(_executing_command),
                        'executing_for_s': (
                            None if exec_since is None
                            else round(time.time() - exec_since, 1)),
                        'command_stuck': bool(stuck_reported),
                        'timers_dead': bool(timers_reported)}))
            except:
                pass
        except:
            pass
        # Sleep on THIS (watchdog) thread only - never the GUI thread
        _watchdog_stop_event.wait(sample_sec)


def start_ai_monitoring():
    """
    Start AI agent monitoring with Qt Timer
    
    CRITICAL FIXES APPLIED:
    - Timer crash recovery
    - Buffer flush timer started
    - Health check timer started
    - Smart polling with mtime
    - Text-to-Speech integration
    """
    global _ai_monitor_timer, _ai_buffer_flush_timer, _ai_health_check_timer, _ai_status_timer, _tts, _tech_reviewer, _ai_watchdog_thread

    if _state.monitoring_active:
        App.Console.PrintWarning("AI monitoring already active!\n")
        return False
    
    if QtCore is None:
        App.Console.PrintError("Qt not available - cannot start monitoring\n")
        return False
    
    # Initialize TTS
    if _tts is None and Config.TTS_ENABLED:
        try:
            _tts = TextToSpeech()
            App.Console.PrintMessage("[TTS] Speech system initialized\n")
        except Exception as e:
            App.Console.PrintWarning(f"[TTS] Could not initialize speech: {e}\n")
            _tts = None
    
    # Setup directories
    if not setup_ai_io_directory():
        App.Console.PrintError("Failed to setup I/O directories\n")
        return False
    
    # CLEAR COMMAND QUEUE ON STARTUP - Prevents old/malformed commands from blocking
    if os.path.exists(AI_INPUT_FILE):
        try:
            # Backup existing commands if file is large (possible debug data)
            file_size = os.path.getsize(AI_INPUT_FILE)
            if file_size > 10240:  # > 10KB suggests accumulated commands
                backup_path = AI_INPUT_FILE + '.backup'
                import shutil
                shutil.copy2(AI_INPUT_FILE, backup_path)
                App.Console.PrintWarning(f"[STARTUP] Large command queue detected ({file_size} bytes)\n")
                App.Console.PrintWarning(f"[STARTUP] Backed up to: {backup_path}\n")
            
            # Clear the command queue
            with open(AI_INPUT_FILE, 'w') as f:
                pass  # Empty the file
            App.Console.PrintMessage("[STARTUP] Command queue cleared for fresh start\n")
        except Exception as e:
            App.Console.PrintWarning(f"[STARTUP] Could not clear command queue: {e}\n")
    
    # Reset runtime state so reconnect/start behaves like a true fresh session
    _state.reset_session()
    for key in ['_last_queue_check_time', '_last_queue_size', '_stuck_position_count', '_last_checked_position']:
        globals().pop(key, None)
    
    # Start monitoring
    _state.monitoring_active = True
    
    # Clear stale shutdown/error fields from previous sessions
    update_status({
        'initialized': datetime.now().isoformat(),
        'monitoring_active': True,
        'last_position': 0,
        'commands_processed': 0,
        'errors_count': 0,
        'consecutive_errors': 0,
        'last_command_time': None,
        'error_state': False,
        'last_error': None,
        'stopped_at': None,
        'freecad_version': f"{App.Version()[0]}.{App.Version()[1]}",
        'ai_bridge_version': Config.VERSION,
        # v5.0.19: monitoring is running, so say so. 5.0.17 reset this to
        # 'starting' at setup and only the watchdog's RECOVERY path ever
        # wrote 'ok', so a healthy Bridge read 'starting' all session.
        'liveness': 'ok',
        'stalled_seconds': 0,
        'stuck_seconds': 0
    })
    
    # v3.4.7: arm the liveness clock before the first timer
    # exists, so a Bridge whose timers never tick even once is
    # still detected.
    _tick('started')
    # Get parent widget to prevent timer garbage collection
    parent = Gui.getMainWindow() if Gui else None
    
    # CRITICAL FIX 1: Command monitor with recovery (with parent to prevent GC)
    _ai_monitor_timer = QtCore.QTimer(parent)
    _ai_monitor_timer.timeout.connect(process_ai_commands_with_recovery)
    _ai_monitor_timer.start(Config.POLL_INTERVAL_MS)
    
    # DEBUG: Verify timer is running
    App.Console.PrintMessage(f"[DEBUG] Timer created: Active={_ai_monitor_timer.isActive()}, Interval={_ai_monitor_timer.interval()}ms\n")
    
    # CRITICAL FIX 2: Buffer flush timer - ACTUALLY START IT!
    _ai_buffer_flush_timer = QtCore.QTimer(parent)
    _ai_buffer_flush_timer.timeout.connect(flush_result_buffer)
    _ai_buffer_flush_timer.start(Config.BUFFER_FLUSH_INTERVAL_MS)
    
    # Status update timer - FIXED: Made global with parent
    _ai_status_timer = QtCore.QTimer(parent)
    _ai_status_timer.timeout.connect(periodic_status_update)
    _ai_status_timer.start(Config.STATUS_UPDATE_INTERVAL_MS)
    
    # Health check timer
    _ai_health_check_timer = QtCore.QTimer(parent)
    _ai_health_check_timer.timeout.connect(update_health_check)
    _ai_health_check_timer.start(Config.HEALTH_CHECK_INTERVAL_MS)

    # v3.3.3: background GUI-freeze watchdog (daemon; detect/warn, never blocks)
    if getattr(Config, 'WATCHDOG_ENABLED', True):
        try:
            _watchdog_stop_event.clear()
            _ai_watchdog_thread = threading.Thread(
                target=_watchdog_loop, name='AIBridgeWatchdog', daemon=True)
            _ai_watchdog_thread.start()
            App.Console.PrintMessage(
                "[OK] GUI-freeze watchdog active (warns after "
                + str(getattr(Config, 'WATCHDOG_WARN_SEC', 30)) + "s)\n")
        except Exception as e:
            App.Console.PrintWarning("[WARN] Watchdog failed to start: " + str(e) + "\n")

    App.Console.PrintMessage("\n" + "="*70 + "\n")
    App.Console.PrintMessage(f"[IMAGINEERING AI BRIDGE v{Config.VERSION}]\n")
    App.Console.PrintMessage("="*70 + "\n\n")
    App.Console.PrintMessage(f"[I/O Directory]: {AI_IO_DIR}\n")
    App.Console.PrintMessage(f"[Learning Directory]: {LEARNING_DIR}\n\n")
    App.Console.PrintMessage("[SECURITY]: Command sandboxing enabled\n")
    App.Console.PrintMessage("[RELIABILITY]: Crash recovery active\n")
    App.Console.PrintMessage("[INTELLIGENCE]: Auto-correction system active\n")
    App.Console.PrintMessage("[PERFORMANCE]: Smart polling with mtime\n")
    App.Console.PrintMessage("[PERSISTENCE]: Auto-flush every 5 seconds\n\n")
    App.Console.PrintMessage("[Input]:  " + AI_INPUT_FILE + "\n")
    App.Console.PrintMessage("[Output]: " + AI_OUTPUT_FILE + "\n")
    App.Console.PrintMessage("[Status]: " + AI_STATUS_FILE + "\n")
    App.Console.PrintMessage("[Health]: " + HEALTH_CHECK_FILE + "\n\n")
    App.Console.PrintMessage("[OK] FreeCAD GUI remains fully responsive!\n")
    App.Console.PrintMessage("[OK] Report View monitoring active!\n")
    App.Console.PrintMessage("="*70 + "\n\n")
    
    # Generate AI Context Summary
    try:
        App.Console.PrintMessage("[AI] Generating context summary for AI assistants...\n")
        generate_ai_context_summary()
    except Exception as e:
        App.Console.PrintWarning(f"[WARN] Could not generate AI context summary: {e}\n")
    
    # Run self-test after delay
    QtCore.QTimer.singleShot(1000, run_comprehensive_self_test)
    
    # Speak startup message
    if _tts and Config.TTS_SPEAK_STARTUP:
        QtCore.QTimer.singleShot(2000, lambda: _tts.speak_startup())
    
    return True

def stop_ai_monitoring():
    """Stop AI monitoring with proper cleanup"""
    global _ai_monitor_timer, _ai_buffer_flush_timer, _ai_health_check_timer, _ai_status_timer, _ai_watchdog_thread

    if not _state.monitoring_active:
        App.Console.PrintWarning("AI monitoring not active!\n")
        return False

    _state.monitoring_active = False

    # v3.3.3: signal the freeze watchdog to stop (daemon thread, exits on its own)
    try:
        _watchdog_stop_event.set()
    except:
        pass
    _ai_watchdog_thread = None

    # Stop and cleanup timers
    for timer in [_ai_monitor_timer, _ai_buffer_flush_timer, _ai_health_check_timer, _ai_status_timer]:
        if timer is not None:
            try:
                timer.timeout.disconnect()
            except (RuntimeError, TypeError) as e:
                # Timer may already be disconnected or deleted
                App.Console.PrintWarning(f"Timer disconnect warning: {e}\n")
                pass
            timer.stop()
            timer.deleteLater()
    
    _ai_monitor_timer = None
    _ai_buffer_flush_timer = None
    _ai_health_check_timer = None
    _ai_status_timer = None
    
    # Force Qt event processing
    if QtCore.QCoreApplication.instance():
        QtCore.QCoreApplication.processEvents()
    
    # Final flush
    flush_result_buffer()
    
    # Final status update
    update_status({
        'monitoring_active': False,
        'stopped_at': datetime.now().isoformat()
    })
    
    # Speak shutdown message
    if _tts and Config.TTS_SPEAK_STARTUP:
        _tts.speak_shutdown()
    
    App.Console.PrintMessage("\n" + "="*70 + "\n")
    App.Console.PrintMessage("[STOPPED] AI AGENT MONITORING STOPPED\n")
    App.Console.PrintMessage("="*70 + "\n\n")
    
    return True

# ============================================================
# SELF-TEST - Comprehensive
# ============================================================

def run_comprehensive_self_test():
    """Comprehensive system test suite - calls run_system_test()"""
    return run_system_test()

# ============================================================
# AI LEARNING SYNTHESIZER - Automated Knowledge Extraction
# ============================================================

class AILearningSynthesizer:
    """
    Automated AI Learning System that:
    1. Reads Python console output from FreeCAD
    2. Parses command I/O logs to understand what happened
    3. Identifies successful patterns and errors
    4. Auto-synthesizes learnings into structured format
    5. Updates knowledge base files automatically
    """
    
    def __init__(self):
        # v4.0.11: four separate guesses, all of them wrong somewhere.
        # technical_data_dir walked exactly two levels up from __file__,
        # which breaks at any other depth; learning_db_path pointed at a
        # SECOND learning database the rest of the Bridge never read; and
        # io_dir pointed at Technical_Data/AI_Agent_IO, which is not where
        # the Bridge's I/O is at all.
        self.technical_data_dir = library_dir()
        self.knowledge_base_path = (
            library_file('FreeCAD_Knowledge_Base.json')
            or os.path.join(self.technical_data_dir,
                            'FreeCAD_Knowledge_Base.json'))
        self.learning_db_path = LEARNING_DB_FILE
        self.community_path = os.path.join(self.technical_data_dir,
                                           'Community_Knowledge')
        self.io_dir = AI_IO_DIR
        
    def read_python_console(self, last_n_chars=5000):
        """Read the FreeCAD Python console/Report View output"""
        try:
            from PySide6 import QtWidgets as QtW
        except ImportError:
            from PySide2 import QtWidgets as QtW
        
        console_text = ""
        try:
            mw = Gui.getMainWindow()
            # Try to find Report View
            report = mw.findChild(QtW.QTextEdit, 'Report view')
            if report:
                content = report.toPlainText()
                console_text = content[-last_n_chars:] if len(content) > last_n_chars else content
            
            # Also try Python console
            python_console = mw.findChild(QtW.QPlainTextEdit)
            if python_console:
                py_content = python_console.toPlainText()
                console_text += "\n--- PYTHON CONSOLE ---\n"
                console_text += py_content[-last_n_chars:] if len(py_content) > last_n_chars else py_content
        except Exception as e:
            App.Console.PrintWarning(f"[Synthesizer] Could not read console: {e}\n")
        
        return console_text
    
    def parse_recent_commands(self, max_commands=20):
        """Parse recent commands from AI_Agent_IO logs"""
        commands = []
        responses = []
        
        try:
            # Read command file
            cmd_file = os.path.join(self.io_dir, 'ai_input_commands.jsonl')
            if os.path.exists(cmd_file):
                with open(cmd_file, 'r', encoding='utf-8') as f:
                    lines = f.readlines()
                    for line in lines[-max_commands:]:
                        try:
                            cmd = json.loads(line.strip())
                            commands.append(cmd)
                        except:
                            pass
            
            # Read response file
            resp_file = os.path.join(self.io_dir, 'ai_output_responses.jsonl')
            if os.path.exists(resp_file):
                with open(resp_file, 'r', encoding='utf-8') as f:
                    lines = f.readlines()
                    for line in lines[-max_commands:]:
                        try:
                            resp = json.loads(line.strip())
                            responses.append(resp)
                        except:
                            pass
        except Exception as e:
            App.Console.PrintWarning(f"[Synthesizer] Could not parse commands: {e}\n")
        
        return commands, responses
    
    def analyze_session(self):
        """Analyze the current session to identify learnable patterns"""
        console_output = self.read_python_console()
        commands, responses = self.parse_recent_commands()
        
        analysis = {
            'timestamp': datetime.now().isoformat(),
            'successful_patterns': [],
            'failed_patterns': [],
            'error_resolutions': [],
            'technique_candidates': [],
            'console_insights': []
        }
        
        # Match commands with responses
        cmd_resp_pairs = []
        for cmd in commands:
            cmd_id = cmd.get('command_id', '')
            matching_resp = None
            for resp in responses:
                if resp.get('command_id', '') == cmd_id:
                    matching_resp = resp
                    break
            cmd_resp_pairs.append((cmd, matching_resp))
        
        # Analyze each pair
        for cmd, resp in cmd_resp_pairs:
            if not cmd:
                continue
            
            code = cmd.get('command', '') or cmd.get('code', '')
            is_success = resp.get('success', False) if resp else False
            error_msg = resp.get('error', '') if resp else ''
            
            pattern = {
                'command_id': cmd.get('command_id', ''),
                'timestamp': cmd.get('timestamp', ''),
                'code_snippet': code[:500],  # First 500 chars
                'success': is_success,
                'error': error_msg
            }
            
            if is_success:
                analysis['successful_patterns'].append(pattern)
                
                # Check if this is a technique candidate
                if any(kw in code.lower() for kw in ['loft', 'bspline', 'polygon', 'fuse', 'cut', 'extrude', 'revolve']):
                    analysis['technique_candidates'].append({
                        'code': code,
                        'category': self._categorize_technique(code),
                        'complexity': 'complex' if len(code) > 200 else 'simple'
                    })
            else:
                analysis['failed_patterns'].append(pattern)
                
                # Check for error resolution (failure followed by success with similar code)
                if error_msg:
                    # Look for subsequent success
                    for later_cmd, later_resp in cmd_resp_pairs:
                        if later_cmd and later_resp:
                            later_code = later_cmd.get('command', '') or later_cmd.get('code', '')
                            if later_resp.get('success', False):
                                # Check similarity
                                if self._code_similarity(code, later_code) > 0.5:
                                    analysis['error_resolutions'].append({
                                        'original_error': error_msg,
                                        'failed_code': code[:300],
                                        'fixed_code': later_code[:300],
                                        'resolution_type': 'code_correction'
                                    })
                                    break
        
        # Parse console for additional insights
        if console_output:
            # Look for specific patterns in console
            lines = console_output.split('\n')
            for line in lines:
                if 'error' in line.lower() or 'warning' in line.lower():
                    analysis['console_insights'].append({
                        'type': 'error' if 'error' in line.lower() else 'warning',
                        'message': line[:200]
                    })
                elif 'success' in line.lower() or 'created' in line.lower():
                    analysis['console_insights'].append({
                        'type': 'success',
                        'message': line[:200]
                    })
        
        return analysis
    
    def _categorize_technique(self, code):
        """Auto-categorize a technique based on code content"""
        code_lower = code.lower()
        if any(kw in code_lower for kw in ['loft', 'sweep', 'bspline', 'bezier']):
            return 'organic_modeling'
        elif any(kw in code_lower for kw in ['beam', 'column', 'slab', 'fem']):
            return 'structural_engineering'
        elif any(kw in code_lower for kw in ['gear', 'thread', 'bolt', 'shaft']):
            return 'mechanical_parts'
        elif any(kw in code_lower for kw in ['wall', 'window', 'door', 'floor']):
            return 'architectural'
        elif any(kw in code_lower for kw in ['fuse', 'cut', 'common', 'fillet']):
            return 'boolean_operations'
        else:
            return 'general_modeling'
    
    def _code_similarity(self, code1, code2):
        """Calculate rough similarity between two code snippets"""
        if not code1 or not code2:
            return 0.0
        
        # Simple word-based similarity
        words1 = set(code1.lower().split())
        words2 = set(code2.lower().split())
        
        if not words1 or not words2:
            return 0.0
        
        intersection = words1.intersection(words2)
        union = words1.union(words2)
        
        return len(intersection) / len(union) if union else 0.0
    
    def synthesize_learning(self, analysis):
        """Convert analysis into structured learning that can update knowledge bases"""
        learning = {
            'synthesis_timestamp': datetime.now().isoformat(),
            'session_id': f"SESSION-{datetime.now().strftime('%Y%m%d-%H%M%S')}",
            'patterns_learned': [],
            'errors_documented': [],
            'techniques_extracted': []
        }
        
        # Process successful patterns
        for pattern in analysis.get('successful_patterns', []):
            code = pattern.get('code_snippet', '')
            if len(code) > 50:  # Only meaningful code
                learning['patterns_learned'].append({
                    'pattern_type': self._categorize_technique(code),
                    'code_example': code,
                    'verified': True,
                    'source': 'auto_capture'
                })
        
        # Process error resolutions (very valuable!)
        for resolution in analysis.get('error_resolutions', []):
            learning['errors_documented'].append({
                'error_type': resolution.get('original_error', '')[:100],
                'failed_approach': resolution.get('failed_code', ''),
                'successful_approach': resolution.get('fixed_code', ''),
                'lesson': f"Corrected from failed approach to working solution",
                'auto_documented': True
            })
        
        # Process technique candidates
        for candidate in analysis.get('technique_candidates', []):
            learning['techniques_extracted'].append({
                'category': candidate.get('category', 'general'),
                'code': candidate.get('code', ''),
                'complexity': candidate.get('complexity', 'unknown'),
                'auto_extracted': True
            })
        
        return learning
    
    def update_knowledge_base(self, learning):
        """Auto-update the FreeCAD_Knowledge_Base.json with new patterns"""
        try:
            # Load existing knowledge base
            kb = {}
            if os.path.exists(self.knowledge_base_path):
                with open(self.knowledge_base_path, 'r', encoding='utf-8') as f:
                    kb = json.load(f)
            
            # Ensure auto_learned_patterns section exists
            if 'auto_learned_patterns' not in kb:
                kb['auto_learned_patterns'] = {
                    'description': 'Patterns automatically extracted by AI Learning Synthesizer',
                    'last_updated': '',
                    'patterns': []
                }
            
            # Add new patterns
            for pattern in learning.get('patterns_learned', []):
                # Check for duplicates (simple check)
                is_duplicate = False
                for existing in kb['auto_learned_patterns']['patterns']:
                    if self._code_similarity(pattern.get('code_example', ''), 
                                             existing.get('code_example', '')) > 0.8:
                        is_duplicate = True
                        break
                
                if not is_duplicate:
                    kb['auto_learned_patterns']['patterns'].append(pattern)
            
            # Update timestamp
            kb['auto_learned_patterns']['last_updated'] = datetime.now().isoformat()
            
            # Update metadata
            if 'metadata' in kb:
                kb['metadata']['last_updated'] = datetime.now().isoformat()
            
            # Save
            with open(self.knowledge_base_path, 'w', encoding='utf-8') as f:
                json.dump(kb, f, indent=2)
            
            App.Console.PrintMessage(f"[Synthesizer] Updated FreeCAD_Knowledge_Base.json with {len(learning.get('patterns_learned', []))} patterns\n")
            return True
            
        except Exception as e:
            App.Console.PrintWarning(f"[Synthesizer] Could not update knowledge base: {e}\n")
            return False
    
    def update_learning_database(self, learning):
        """Auto-update the AI_Learning_Database.json"""
        try:
            # Load existing database
            db = {}
            if os.path.exists(self.learning_db_path):
                with open(self.learning_db_path, 'r', encoding='utf-8') as f:
                    db = json.load(f)
            
            # Add to knowledge_updates in metadata
            if 'metadata' not in db:
                db['metadata'] = {'knowledge_updates': []}
            if 'knowledge_updates' not in db['metadata']:
                db['metadata']['knowledge_updates'] = []
            
            # Create update entry
            update_entry = {
                'date': datetime.now().strftime('%Y-%m-%d'),
                'session': learning.get('session_id', 'auto_session'),
                'auto_synthesized': True,
                'patterns_count': len(learning.get('patterns_learned', [])),
                'errors_count': len(learning.get('errors_documented', [])),
                'techniques_count': len(learning.get('techniques_extracted', []))
            }
            
            db['metadata']['knowledge_updates'].append(update_entry)
            db['metadata']['last_updated'] = datetime.now().isoformat()
            
            # Add error resolutions to database
            if 'error_resolutions' not in db:
                db['error_resolutions'] = []
            
            for error in learning.get('errors_documented', []):
                db['error_resolutions'].append({
                    'timestamp': datetime.now().isoformat(),
                    'error_type': error.get('error_type', ''),
                    'failed_approach': error.get('failed_approach', ''),
                    'successful_approach': error.get('successful_approach', ''),
                    'auto_documented': True
                })
            
            # Save
            with open(self.learning_db_path, 'w', encoding='utf-8') as f:
                json.dump(db, f, indent=2)
            
            App.Console.PrintMessage(f"[Synthesizer] Updated AI_Learning_Database.json\n")
            return True
            
        except Exception as e:
            App.Console.PrintWarning(f"[Synthesizer] Could not update learning database: {e}\n")
            return False
    
    def save_synthesized_technique(self, learning):
        """Save extracted techniques to Community_Knowledge/Verified/"""
        try:
            verified_dir = os.path.join(self.community_path, 'Verified')
            os.makedirs(verified_dir, exist_ok=True)
            
            saved_count = 0
            for technique in learning.get('techniques_extracted', []):
                if technique.get('complexity') == 'complex':  # Only save complex techniques
                    tech_id = f"AUTO-{datetime.now().strftime('%Y%m%d-%H%M%S')}-{saved_count}"
                    
                    tech_doc = {
                        'technique_id': tech_id,
                        'contributor': 'AI_Learning_Synthesizer',
                        'date': datetime.now().strftime('%Y-%m-%d'),
                        'category': technique.get('category', 'general'),
                        'title': f"Auto-extracted {technique.get('category', 'technique')}",
                        'solution': {
                            'code_example': technique.get('code', ''),
                            'auto_extracted': True
                        },
                        'verified': True,
                        'verification_source': 'successful_execution',
                        'capture_timestamp': datetime.now().isoformat()
                    }
                    
                    filename = f"{tech_id}.json"
                    filepath = os.path.join(verified_dir, filename)
                    
                    with open(filepath, 'w', encoding='utf-8') as f:
                        json.dump(tech_doc, f, indent=2)
                    
                    saved_count += 1
            
            if saved_count > 0:
                App.Console.PrintMessage(f"[Synthesizer] Saved {saved_count} techniques to Community_Knowledge\n")
            
            return saved_count
            
        except Exception as e:
            App.Console.PrintWarning(f"[Synthesizer] Could not save techniques: {e}\n")
            return 0
    
    def run_full_synthesis(self):
        """Run the complete synthesis pipeline"""
        App.Console.PrintMessage("\n" + "="*60 + "\n")
        App.Console.PrintMessage("[AI Learning Synthesizer] Starting automated analysis...\n")
        App.Console.PrintMessage("="*60 + "\n")
        
        # Step 1: Analyze session
        App.Console.PrintMessage("[1/4] Analyzing session data...\n")
        analysis = self.analyze_session()
        
        App.Console.PrintMessage(f"  - Found {len(analysis['successful_patterns'])} successful patterns\n")
        App.Console.PrintMessage(f"  - Found {len(analysis['failed_patterns'])} failed patterns\n")
        App.Console.PrintMessage(f"  - Found {len(analysis['error_resolutions'])} error resolutions\n")
        App.Console.PrintMessage(f"  - Found {len(analysis['technique_candidates'])} technique candidates\n")
        
        # Step 2: Synthesize learning
        App.Console.PrintMessage("[2/4] Synthesizing learnings...\n")
        learning = self.synthesize_learning(analysis)
        
        # Step 3: Update knowledge bases
        App.Console.PrintMessage("[3/4] Updating knowledge bases...\n")
        self.update_knowledge_base(learning)
        self.update_learning_database(learning)
        
        # Step 4: Save techniques
        App.Console.PrintMessage("[4/4] Saving extracted techniques...\n")
        saved = self.save_synthesized_technique(learning)
        
        App.Console.PrintMessage("="*60 + "\n")
        App.Console.PrintMessage("[AI Learning Synthesizer] Complete!\n")
        App.Console.PrintMessage(f"  Patterns added: {len(learning['patterns_learned'])}\n")
        App.Console.PrintMessage(f"  Errors documented: {len(learning['errors_documented'])}\n")
        App.Console.PrintMessage(f"  Techniques saved: {saved}\n")
        App.Console.PrintMessage("="*60 + "\n\n")
        
        return {
            'analysis': analysis,
            'learning': learning,
            'techniques_saved': saved
        }


# ============================================================
# TECHNIQUE CAPTURE DIALOG (Enhanced with Auto-Synthesis)
# ============================================================

class TechniqueCaptureDialog(QtWidgets.QDialog):
    """Dialog for capturing and documenting techniques - now with AI auto-synthesis"""
    
    def __init__(self, command_data, parent=None):
        super(TechniqueCaptureDialog, self).__init__(parent)
        self.command_data = command_data
        self.synthesizer = AILearningSynthesizer()
        self.setWindowTitle("AI Learning Synthesizer")
        self.setMinimumWidth(700)
        self.setMinimumHeight(600)
        self.setup_ui()
    
    def setup_ui(self):
        layout = QtWidgets.QVBoxLayout(self)
        
        # Header
        header = QtWidgets.QLabel("<h2>AI Learning Synthesizer</h2>")
        header.setAlignment(Qt.AlignCenter)
        layout.addWidget(header)
        
        info_label = QtWidgets.QLabel(
            "<b>Automatic Knowledge Extraction</b><br>"
            "This tool reads the Python console, analyzes command history, and automatically<br>"
            "synthesizes learnings into the knowledge base for future AI sessions."
        )
        info_label.setWordWrap(True)
        info_label.setAlignment(Qt.AlignCenter)
        layout.addWidget(info_label)
        
        # Status area
        self.status_group = QtWidgets.QGroupBox("Session Analysis")
        status_layout = QtWidgets.QVBoxLayout()
        
        self.status_text = QtWidgets.QTextEdit()
        self.status_text.setReadOnly(True)
        self.status_text.setStyleSheet("font-family: monospace; font-size: 10pt; background-color: #1a1a2e;")
        self.status_text.setMinimumHeight(300)
        status_layout.addWidget(self.status_text)
        
        self.status_group.setLayout(status_layout)
        layout.addWidget(self.status_group)
        
        # Progress bar
        self.progress = QtWidgets.QProgressBar()
        self.progress.setRange(0, 100)
        self.progress.setValue(0)
        layout.addWidget(self.progress)
        
        # Buttons
        btn_layout = QtWidgets.QHBoxLayout()
        
        self.synthesize_btn = QtWidgets.QPushButton("🚀 Run Auto-Synthesis")
        self.synthesize_btn.setStyleSheet("background-color: #4a9eff; font-weight: bold; font-size: 12pt; padding: 10px;")
        self.synthesize_btn.clicked.connect(self.run_synthesis)
        btn_layout.addWidget(self.synthesize_btn)
        
        close_btn = QtWidgets.QPushButton("Close")
        close_btn.clicked.connect(self.accept)
        btn_layout.addWidget(close_btn)
        
        layout.addLayout(btn_layout)
        
        # Pre-analyze to show current state
        self.preview_analysis()
    
    def preview_analysis(self):
        """Show preview of what will be analyzed"""
        self.status_text.clear()
        self.status_text.append("=" * 50)
        self.status_text.append("📋 SESSION PREVIEW")
        self.status_text.append("=" * 50)
        
        # Quick analysis
        analysis = self.synthesizer.analyze_session()
        
        self.status_text.append(f"\n✅ Successful commands: {len(analysis['successful_patterns'])}")
        self.status_text.append(f"❌ Failed commands: {len(analysis['failed_patterns'])}")
        self.status_text.append(f"🔧 Error resolutions: {len(analysis['error_resolutions'])}")
        self.status_text.append(f"💡 Technique candidates: {len(analysis['technique_candidates'])}")
        self.status_text.append(f"📝 Console insights: {len(analysis['console_insights'])}")
        
        if analysis['technique_candidates']:
            self.status_text.append("\n--- TECHNIQUE CANDIDATES ---")
            for i, tech in enumerate(analysis['technique_candidates'][:5]):
                self.status_text.append(f"  [{i+1}] {tech['category']} ({tech['complexity']})")
        
        if analysis['error_resolutions']:
            self.status_text.append("\n--- ERROR RESOLUTIONS FOUND ---")
            for i, res in enumerate(analysis['error_resolutions'][:3]):
                self.status_text.append(f"  [{i+1}] {res['original_error'][:50]}...")
        
        self.status_text.append("\n" + "=" * 50)
        self.status_text.append("Click 'Run Auto-Synthesis' to update knowledge bases")
        self.status_text.append("=" * 50)
    
    def run_synthesis(self):
        """Run the full synthesis pipeline"""
        self.synthesize_btn.setEnabled(False)
        self.synthesize_btn.setText("⏳ Synthesizing...")
        self.status_text.clear()
        
        self.progress.setValue(10)
        self.status_text.append("🔍 Reading Python console output...")
        QtWidgets.QApplication.processEvents()
        
        self.progress.setValue(25)
        self.status_text.append("Analyzing command history...")
        QtWidgets.QApplication.processEvents()
        
        # Run full synthesis
        result = self.synthesizer.run_full_synthesis()
        
        self.progress.setValue(75)
        self.status_text.append("\n" + "=" * 50)
        self.status_text.append("📝 SYNTHESIS COMPLETE")
        self.status_text.append("=" * 50)
        
        analysis = result['analysis']
        learning = result['learning']
        
        self.status_text.append(f"\n✅ Patterns learned: {len(learning['patterns_learned'])}")
        self.status_text.append(f"Errors documented: {len(learning['errors_documented'])}")
        self.status_text.append(f"💾 Techniques saved: {result['techniques_saved']}")
        
        self.status_text.append("\n--- KNOWLEDGE BASES UPDATED ---")
        self.status_text.append("  ✓ FreeCAD_Knowledge_Base.json")
        self.status_text.append("  ✓ AI_Learning_Database.json")
        if result['techniques_saved'] > 0:
            self.status_text.append("  ✓ Community_Knowledge/Verified/")
        
        self.status_text.append("\n" + "=" * 50)
        self.status_text.append("🎉 Future AI agents will learn from this session!")
        self.status_text.append("=" * 50)
        
        self.progress.setValue(100)
        self.synthesize_btn.setText("Synthesis Complete")
        self.synthesize_btn.setStyleSheet("background-color: #28a745; font-weight: bold; font-size: 12pt; padding: 10px;")

# ============================================================
# QUICK CAPTURE DIALOG - Simple Technique Submission
# ============================================================

class QuickCaptureDialog(QtWidgets.QDialog):
    """Simple dialog for quickly capturing a technique with minimal input"""
    
    def __init__(self, command_data, parent=None):
        super(QuickCaptureDialog, self).__init__(parent)
        self.command_data = command_data
        self.setWindowTitle("Quick Capture Technique")
        self.setMinimumWidth(550)
        self.setMinimumHeight(400)
        self.setup_ui()
    
    def setup_ui(self):
        layout = QtWidgets.QVBoxLayout(self)
        
        # Header
        header = QtWidgets.QLabel("<h2>Quick Capture</h2>")
        header.setAlignment(Qt.AlignCenter)
        layout.addWidget(header)
        
        info = QtWidgets.QLabel(
            "Give this technique a name and category to save it for future AI agents."
        )
        info.setWordWrap(True)
        info.setAlignment(Qt.AlignCenter)
        info.setStyleSheet("color: #aaaaaa; padding: 10px;")
        layout.addWidget(info)
        
        # Form
        form = QtWidgets.QFormLayout()
        
        # Title (required)
        self.title_edit = QtWidgets.QLineEdit()
        self.title_edit.setPlaceholderText("e.g., 'Tapered Loft from Polygons'")
        self.title_edit.setStyleSheet("padding: 8px; font-size: 11pt;")
        form.addRow("Technique Name:", self.title_edit)
        
        # Category
        self.category_combo = QtWidgets.QComboBox()
        self.category_combo.addItems([
            "organic_modeling",
            "structural_engineering",
            "mechanical_parts",
            "boolean_operations",
            "architectural",
            "workflow_optimization",
            "error_fix"
        ])
        self.category_combo.setStyleSheet("padding: 5px;")
        form.addRow("Category:", self.category_combo)
        
        # Quick notes (optional)
        self.notes_edit = QtWidgets.QLineEdit()
        self.notes_edit.setPlaceholderText("Optional: What makes this useful? (one line)")
        form.addRow("Quick Note:", self.notes_edit)
        
        layout.addLayout(form)
        
        # Show captured command preview
        preview_group = QtWidgets.QGroupBox("Captured Command")
        preview_layout = QtWidgets.QVBoxLayout()
        
        preview = self.command_data.get('command_preview', 
                                        self.command_data.get('stdout', 'No preview'))
        self.preview_text = QtWidgets.QTextEdit()
        self.preview_text.setPlainText(preview[:500])
        self.preview_text.setReadOnly(True)
        self.preview_text.setMaximumHeight(100)
        self.preview_text.setStyleSheet("font-family: monospace; font-size: 9pt; background-color: #1a1a2e;")
        preview_layout.addWidget(self.preview_text)
        
        preview_group.setLayout(preview_layout)
        layout.addWidget(preview_group)
        
        # Buttons
        btn_layout = QtWidgets.QHBoxLayout()
        
        save_btn = QtWidgets.QPushButton("💾 Save Technique")
        save_btn.setStyleSheet("background-color: #28a745; font-weight: bold; padding: 12px; font-size: 11pt;")
        save_btn.clicked.connect(self.save_technique)
        btn_layout.addWidget(save_btn)
        
        cancel_btn = QtWidgets.QPushButton("Cancel")
        cancel_btn.setStyleSheet("padding: 12px;")
        cancel_btn.clicked.connect(self.reject)
        btn_layout.addWidget(cancel_btn)
        
        layout.addLayout(btn_layout)
    
    def save_technique(self):
        """Save the technique with minimal processing"""
        title = self.title_edit.text().strip()
        if not title:
            QtWidgets.QMessageBox.warning(self, "Required", "Please enter a technique name.")
            return
        
        # Generate ID
        now = datetime.now()
        tech_id = f"QUICK-{now.strftime('%Y%m%d-%H%M%S')}"
        
        technique = {
            "technique_id": tech_id,
            "contributor": "User",
            "date": now.strftime('%Y-%m-%d'),
            "category": self.category_combo.currentText(),
            "title": title,
            "solution": {
                "code_example": self.preview_text.toPlainText(),
                "quick_note": self.notes_edit.text().strip()
            },
            "verified": True,
            "verification_source": "user_captured",
            "command_id": self.command_data.get('command_id', 'unknown'),
            "capture_timestamp": now.isoformat()
        }
        
        try:
            # Save to Verified folder (user-captured = verified)
            verified_dir = os.path.join(
                os.path.dirname(os.path.dirname(os.path.abspath(__file__))), 'Macro_03', 'Technical_Data', 'Community_Knowledge', 'Verified'
            )
            os.makedirs(verified_dir, exist_ok=True)
            
            filename = f"{tech_id}_{title.replace(' ', '_')[:25]}.json"
            filepath = os.path.join(verified_dir, filename)
            
            with open(filepath, 'w', encoding='utf-8') as f:
                json.dump(technique, f, indent=2)
            
            App.Console.PrintMessage(f"\n[CAPTURED] ✅ Technique saved: {filename}\n")
            
            QtWidgets.QMessageBox.information(
                self, "Saved!",
                f"✅ Technique captured!\n\n"
                f"Name: {title}\n"
                f"Category: {self.category_combo.currentText()}\n"
                f"File: {filename}\n\n"
                f"Future AI agents will learn from this!"
            )
            self.accept()
            
        except Exception as e:
            QtWidgets.QMessageBox.warning(self, "Error", f"Could not save:\n{str(e)}")

# ============================================================
# GUI CONFIGURATION DIALOG
# ============================================================

# Imagineering standard palette (Macro_Training.md Rule 12)
BG_COLOR = "#1e1e2e"
CARD_COLOR = "#2a2a3d"
TEXT_COLOR = "#e0e0e0"
ACCENT_GREEN = "#39ff14"
ACCENT_CYAN = "#00bcd4"
ACCENT_BLUE = "#3f51b5"
CANCEL_RED = "#F4424D"


# ===========================================================================
# Rule 12 Support & Donation block, verbatim from AI_Project_Log 0.0.12,
# which took it verbatim from 002_Program_Window_0.0.45. GradientLogoLabel is
# NOT copied: this file already has its own, just below.
# ===========================================================================
PAYPAL_SVG_B64 = (
    "PHN2ZyB4bWxucz0iaHR0cDovL3d3dy53My5vcmcvMjAwMC9zdmciIHZpZXdCb3g9IjAgMCAyNCAy"
    "NCIgd2lkdGg9IjI0IiBoZWlnaHQ9IjI0Ij4KPHBhdGggZD0iTTcuMDc2IDIxLjMzN0gyLjQ3YS42"
    "NDEuNjQxIDAgMCAxLS42MzMtLjc0TDQuOTQ0LjkwMUM1LjAyNi4zODIgNS40NzQgMCA1Ljk5OCAw"
    "aDcuNDZjMi41NyAwIDQuNTc4LjU0MyA1LjY5IDEuODEgMS4wMSAxLjE1IDEuMzA0IDIuNDIgMS4w"
    "MTIgNC4yODctLjAyMy4xNDMtLjA0Ny4yODgtLjA3Ny40MzctLjk4MyA1LjA1LTQuMzQ5IDYuNzk3"
    "LTguNjQ3IDYuNzk3SDkuNjAzYy0uNTY0IDAtMS4wNC40MDgtMS4xMy45NjRMNy4wNzYgMjEuMzM3"
    "eiIgZmlsbD0iIzAwMzA4NyIvPgo8cGF0aCBkPSJNMTguMDkzIDcuMDZjLS4wMjMuMTQzLS4wNDcu"
    "Mjg4LS4wNzcuNDM3LS45ODMgNS4wNS00LjM0OSA2Ljc5Ny04LjY0NyA2Ljc5N0g3LjUzNmMtLjU2"
    "NCAwLTEuMDQuNDA4LTEuMTMuOTY0TDUuMTEgMjIuOTAzYS41NTQuNTU0IDAgMCAwIC41NDYuNjQy"
    "aDMuODMyYy40OTQgMCAuOTE0LS4zNTcuOTkxLS44NDNsLjA0LS4yMDcuNzktNC45ODEuMDUtLjI3"
    "MWMuMDc3LS40ODYuNDk3LS44NDMuOTkxLS44NDNoLjYyNGM0LjA0MyAwIDcuMjA1LTEuNjQyIDgu"
    "MTMtNi4zOTMuMzg2LTEuOTgzLjE4Ni0zLjYzOC0uODM2LTQuODAxYTMuOTcgMy45NyAwIDAgMC0x"
    "LjE3NS0uOTQ2eiIgZmlsbD0iIzAwNzBFMCIvPgo8L3N2Zz4="
)

KOFI_SVG_B64 = (
    "PHN2ZyB4bWxucz0iaHR0cDovL3d3dy53My5vcmcvMjAwMC9zdmciIHZpZXdCb3g9IjAgMCAyNCAy"
    "NCIgd2lkdGg9IjI0IiBoZWlnaHQ9IjI0Ij4KPHBhdGggZD0iTTIzLjg4MSA4Ljk0OGMtLjc3My00"
    "LjA4NS00Ljg1OS00LjU5My00Ljg1OS00LjU5M0guNzIzYy0uNjA0IDAtLjY3OS43OTgtLjY3OS43"
    "OThzLS4wODIgNy4zMjQtLjAyMiAxMS44MjJjLjE2NCAyLjQyNCAyLjU4NiAyLjY3MiAyLjU4NiAy"
    "LjY3MnM4LjI2Ny0uMDIzIDExLjk2Ni0uMDQ5YzIuNDM4LS40MjYgMi42ODMtMi41NjYgMi42NTgt"
    "My43MzQgNC4zNTIuMjQgNy40MjItMi44MzEgNy42NDktNi45MTZ6bS0xMS4wNjIgMy41Yy0xLjI5"
    "IDAtNS41NjIuMDUtNS41NjIuMDVzLS4yMjYtNS40LS4xMjMtNy4zNjVoNS42ODVjMi43IDAgMi43"
    "IDMuNjU4IDIuNyAzLjY1OFMxNS41MiAxMi40NDggMTIuODIgMTIuNDQ4em04LjE0NS0xLjM5OWMt"
    "LjQyNiAxLjk2NC0yLjEzNCAyLjg4Mi0zLjc4MyAyLjk2VjguMTU2YzEuOS4yIDQuMjEgMS4wMjQg"
    "My43ODMgMi44OTN6IiBmaWxsPSIjRkY1RTVCIi8+CjxwYXRoIGQ9Ik04LjcyNyA3LjUwNGMtLjM2"
    "LS4wODUtLjczNy4xNS0uODM1LjUyMi0uMDk4LjM3Mi4xMTIuNzQ2LjQ3LjgzMi4zNi4wODUuNzM3"
    "LS4xNS44MzUtLjUyMi4wOTgtLjM3Mi0uMTEyLS43NDYtLjQ3LS44MzJ6TTYuMjY0IDcuNTA0Yy0u"
    "MzYtLjA4NS0uNzM3LjE1LS44MzUuNTIyLS4wOTguMzcyLjExMi43NDYuNDcuODMyLjM2LjA4NS43"
    "MzctLjE1LjgzNS0uNTIyLjA5OC0uMzcyLS4xMTItLjc0Ni0uNDctLjgzMnoiIGZpbGw9IiNmZmYi"
    "Lz4KPC9zdmc+"
)

STRIPE_SVG_B64 = (
    "PHN2ZyB4bWxucz0iaHR0cDovL3d3dy53My5vcmcvMjAwMC9zdmciIHZpZXdCb3g9IjAgMCAyNCAy"
    "NCIgd2lkdGg9IjI0IiBoZWlnaHQ9IjI0Ij4KPHJlY3Qgcng9IjQiIHdpZHRoPSIyNCIgaGVpZ2h0"
    "PSIyNCIgZmlsbD0iIzYzNUJGRiIvPgo8cGF0aCBkPSJNMTIuNSA3LjJjMC0uOC43LTEuMiAxLjct"
    "MS4yIDEuNSAwIDMuNC41IDQuOSAxLjNWMy43Yy0xLjYtLjctMy4zLTEtNC45LTEtNCAwLTYuNyAy"
    "LjEtNi43IDUuNiAwIDUuNSA3LjUgNC42IDcuNSA3IDAgMS0uOCAxLjMtMiAxLjMtMS43IDAtMy45"
    "LS43LTUuNi0xLjd2My43YzEuOS44IDMuOCAxLjIgNS42IDEuMiA0LjEgMCA2LjktMiA2LjktNS42"
    "LS4xLTUuOS03LjQtNC45LTcuNC03eiIgZmlsbD0iI2ZmZiIvPgo8L3N2Zz4="
)


def icon_from_b64(b64_str, size=20):
    """Decode a base64 SVG string into a QIcon."""
    svg_bytes = base64.b64decode(b64_str)
    pixmap = QtGui.QPixmap()
    pixmap.loadFromData(svg_bytes, "SVG")
    return QtGui.QIcon(pixmap.scaled(size, size,
        QtCore.Qt.AspectRatioMode.KeepAspectRatio,
        QtCore.Qt.TransformationMode.SmoothTransformation))

# ── Splash Window (embedded) ──────────────────────────────────────
SPLASH_BUTTONS = [
    {"label": "Website",       "url": "https://sites.google.com/view/imagineering/home"},
    {"label": "Documentation", "url": "https://sites.google.com/view/imagineering/home/resources/freecad-macros/002_program_window_0-0-44-fcmacro"},
    {"label": "Presentation",  "url": "https://youtu.be/JvdpJoyODm0"},
]

SPLASH_BG       = "#1e1e2e"
SPLASH_CARD     = "#2a2a3d"
SPLASH_TEXT     = "#e0e0e0"
SPLASH_GREEN    = "#39ff14"
SPLASH_CYAN     = "#00bcd4"
SPLASH_BLUE     = "#3f51b5"
SPLASH_BTN_COLORS = [SPLASH_GREEN, SPLASH_CYAN, SPLASH_BLUE]




class DonationPanel(QtWidgets.QWidget):
    """Support label above the three donation buttons."""

    # Splash theme colours
    BG_COLOR     = "#1e1e2e"
    CARD_COLOR   = "#2a2a3d"
    TEXT_COLOR   = "#e0e0e0"
    ACCENT_GREEN = "#39ff14"
    ACCENT_CYAN  = "#00bcd4"
    ACCENT_BLUE  = "#3f51b5"

    def __init__(self, parent=None):
        super().__init__(parent)
        main_layout = QtWidgets.QVBoxLayout(self)
        main_layout.setContentsMargins(4, 0, 4, 2)
        main_layout.setSpacing(0)


        # 2) "Support & Donation" label (raised 3mm via reduced spacing)
        donate_label = QtWidgets.QLabel("Support & Donation")
        donate_label.setAlignment(QtCore.Qt.AlignmentFlag.AlignCenter)
        donate_label.setFixedHeight(18)
        donate_label.setStyleSheet(
            f"font-weight: bold; font-size: 13px; padding: 0px; margin: 0px;"
            f"color: {self.ACCENT_CYAN}; background: transparent;"
            f"letter-spacing: 1px;")
        main_layout.addWidget(donate_label)

        # 3) Donation buttons (bottom) - larger, themed, shifted ~3mm left
        donate_layout = QtWidgets.QHBoxLayout()
        donate_layout.setContentsMargins(0, 0, 22, 0)  # extra right margin shifts left
        donate_layout.setSpacing(10)

        btn_style = (
            f"QPushButton {{"
            f"  font-size: 12px; font-weight: bold; padding: 8px 14px;"
            f"  background: {self.CARD_COLOR}; color: {self.TEXT_COLOR};"
            f"  border: 1.5px solid {self.ACCENT_CYAN}; border-radius: 4px;"
            f"}}"
            f"QPushButton:hover {{"
            f"  background: {self.ACCENT_CYAN}; color: {self.BG_COLOR};"
            f"}}"
        )

        # PayPal
        paypal_btn = QtWidgets.QPushButton("  PayPal")
        paypal_btn.setIcon(icon_from_b64(PAYPAL_SVG_B64, 22))
        paypal_btn.setIconSize(QtCore.QSize(22, 22))
        paypal_btn.setCursor(QtCore.Qt.CursorShape.PointingHandCursor)
        paypal_btn.setStyleSheet(btn_style)
        paypal_btn.clicked.connect(lambda: webbrowser.open(
            "https://www.paypal.com/donate/?business=NNPHQ2ZKBRZCG&no_recurring=0"
            "&item_name=If+you%E2%80%99d+like+to+support+the+channel%2C+donations"
            "+are+greatly+appreciated+and+will+help+me+create+the+next+video."
            "&currency_code=AUD"))
        donate_layout.addWidget(paypal_btn)

        # Ko-fi
        kofi_btn = QtWidgets.QPushButton("  Ko-fi")
        kofi_btn.setIcon(icon_from_b64(KOFI_SVG_B64, 22))
        kofi_btn.setIconSize(QtCore.QSize(22, 22))
        kofi_btn.setCursor(QtCore.Qt.CursorShape.PointingHandCursor)
        kofi_btn.setStyleSheet(btn_style)
        kofi_btn.setToolTip("Support on Ko-fi")
        kofi_btn.clicked.connect(lambda: webbrowser.open(
            "https://ko-fi.com/imagineering_au"))
        donate_layout.addWidget(kofi_btn)

        # Stripe
        stripe_btn = QtWidgets.QPushButton("  Stripe")
        stripe_btn.setIcon(icon_from_b64(STRIPE_SVG_B64, 22))
        stripe_btn.setIconSize(QtCore.QSize(22, 22))
        stripe_btn.setCursor(QtCore.Qt.CursorShape.PointingHandCursor)
        stripe_btn.setStyleSheet(btn_style)
        stripe_btn.setToolTip("Support via Stripe")
        stripe_btn.clicked.connect(lambda: webbrowser.open(
            "https://buy.stripe.com/00wcN6bhXgj200Nb4fcZa00"))
        donate_layout.addWidget(stripe_btn)

        main_layout.addLayout(donate_layout)


# ── Original Macro ─────────────────────────────────────────────────


# ============================================================
# BACKUP AND FORK
# ============================================================
# "Ensure you backup & rename the document to create forks of your work
# daily at a minimum" -- the operator, and they are right. An AI driving a
# CAD document can do a great deal of damage quickly and politely, and
# undo is one linear stack that a recompute can swallow. A dated copy on
# disk is the only thing that survives being wrong.

FORK_DUE_COMMANDS = 20          # Bridge commands since the last fork


def _fork_record_file():
    """Where the fork history lives: beside the Bridge config, not inside
    the document. A record kept in the file it is protecting is no record
    at all."""
    return os.path.join(os.path.dirname(AI_CONFIG_FILE), "ai_forks.json")


def _fork_load():
    try:
        with open(_fork_record_file(), "r", encoding="utf-8") as fh:
            return json.load(fh) or {}
    except BaseException:
        return {}


def _fork_key(doc):
    try:
        return os.path.normcase(os.path.abspath(doc.FileName or doc.Name))
    except BaseException:
        return ""






def fork_state(doc):
    """When this document was last forked, and whether one is due.

    Never raises and never writes. A reminder that can break the panel it
    lives in is worse than no reminder.
    """
    out = {"saved": False, "last": None, "last_iso": "", "today": False,
           "since": 0, "due": True, "why": "no document"}
    try:
        if doc is None:
            return out
        fn = getattr(doc, "FileName", "") or ""
        out["saved"] = bool(fn) and os.path.exists(fn)
        if not out["saved"]:
            out["why"] = ("this document has never been saved, so there is "
                          "nothing to fork from")
            return out
        rec = _fork_load().get(_fork_key(doc)) or {}
        out["last"] = rec.get("path") or None
        out["last_iso"] = rec.get("when") or ""
        at = float(rec.get("at") or 0)
        cmds_at = int(rec.get("commands") or 0)
        try:
            done = int(_state.get_stats().get("commands_processed") or 0)
        except BaseException:
            done = 0
        out["since"] = max(0, done - cmds_at)
        if not at:
            out["why"] = "no fork of this document has been taken yet"
            return out
        out["today"] = (time.strftime("%Y-%m-%d", time.localtime(at))
                        == time.strftime("%Y-%m-%d"))
        mins = (time.time() - at) / 60.0
        if not out["today"]:
            out["why"] = ("the last fork is not from today (%s)"
                          % time.strftime("%d %b %H:%M", time.localtime(at)))
        elif out["since"] >= FORK_DUE_COMMANDS:
            out["why"] = ("%d Bridge commands have run since the last fork"
                          % out["since"])
        # The "unsaved changes for N minutes" rule USED to be here and is
        # deliberately gone. Measured on 26.3, there is no Document flag
        # that answers it:
        #     isTouched()  means "has a pending recompute" and goes False
        #                  again the moment anything recomputes -- which
        #                  the GUI does constantly
        #     isSaved()    stays True after an edit
        #     Modified     does not exist on the Document at all
        # So the clause was reading "pending recompute" and calling it
        # unsaved work. It fired on any older file, which FreeCAD marks
        # on open, and stopped firing the instant a recompute ran. Both
        # wrong, in opposite directions.
        #
        # What remains is measured and true: a fork not from today, and
        # the count of Bridge commands since the last one. A rule that
        # cannot be measured does not belong in a reminder the operator
        # is meant to trust.
        else:
            out["due"] = False
            out["why"] = ("last fork %s, %d commands since"
                          % (time.strftime("%H:%M", time.localtime(at)),
                             out["since"]))
    except BaseException as exc:
        out["why"] = "could not read the fork history: %s" % exc
    return out


def do_fork(doc):
    """Save the document, then write a dated numbered copy beside it.

    saveCopy, not saveAs: the operator stays in the file they were working
    in. A button that silently moves you into a new file is how you end up
    with the last hour of work in a document you did not know you were in.
    """
    try:
        if doc is None:
            return False, "There is no active document to fork.", ""
        fn = getattr(doc, "FileName", "") or ""
        if not fn:
            return (False,
                    "Save the document once first -- a fork needs somewhere "
                    "to go.", "")
        doc.save()
        folder = os.path.join(os.path.dirname(fn), "Forks")
        os.makedirs(folder, exist_ok=True)
        stem = os.path.splitext(os.path.basename(fn))[0]
        day = time.strftime("%Y%m%d")
        i = 1
        while True:
            path = os.path.join(folder, "%s_%s_%02d.FCStd" % (stem, day, i))
            if not os.path.exists(path):
                break
            i += 1
            if i > 99:
                return (False,
                        "99 forks of this document today already. Tidy the "
                        "Forks folder before taking another.", "")
        doc.saveCopy(path)
        if not os.path.exists(path):
            return (False,
                    "saveCopy reported no error but wrote nothing to %s"
                    % path, "")
        try:
            rec = _fork_load()
            try:
                done = int(_state.get_stats().get("commands_processed") or 0)
            except BaseException:
                done = 0
            rec[_fork_key(doc)] = {
                "path": path, "at": time.time(), "commands": done,
                "when": time.strftime("%Y-%m-%d %H:%M:%S")}
            with open(_fork_record_file(), "w", encoding="utf-8") as fh:
                json.dump(rec, fh, indent=2)
        except BaseException:
            pass        # the copy exists; losing the bookkeeping is minor
        return (True,
                "Saved, and forked to %s (%.1f MB)."
                % (os.path.basename(path),
                   os.path.getsize(path) / 1048576.0), path)
    except BaseException as exc:
        return False, "The fork failed: %s" % exc, ""


# ===========================================================================
# AI PROJECT LOG -- spliced in whole from AI_Project_Log_0.0.12.FCMacro
# ---------------------------------------------------------------------------
# Keeps a Markdown log beside and inside the .FCStd so any agent can resume a
# project, and measures the document's geometry before anyone touches it.
# Two names were changed on the way in, and only two:
#
#   import datetime      -> import datetime as _log_datetime
#       because this file does `from datetime import datetime` and uses the
#       CLASS 78 times. Rebinding the name breaks every one of them.
#   __Version__          -> __LOG_VERSION__
#       because FreeCAD reads __Version__ as this macro's own version.
#
# Everything else is as written and as tested: 188 headless checks across six
# suites, 87 of them on the document inventory alone.
# ===========================================================================
__LOG_VERSION__ = '0.0.12'

import os
import re
import sys
import queue
import atexit
import hashlib
import threading
import datetime as _log_datetime

import FreeCAD as App
import FreeCADGui as Gui

# ----------------------------------------------------------------------------
# Settings: everything tunable lives here so it is easy to audit.
# ----------------------------------------------------------------------------
FLUSH_INTERVAL_S   = 1.0        # how often the writer thread flushes to disk
CHAPTER_MAX_BYTES  = 400_000    # roll to a new chapter beyond this size
MAX_LINE_CHARS     = 4_000      # trim single very long lines
MAX_BLOCK_LINES    = 400        # trim very long output blocks
QUEUE_MAX          = 20_000     # ceiling on queued entries; see put()
LOG_SUFFIX         = ".ai_log"  # MyPart.FCStd -> MyPart.ai_log/ folder
META_FLAG_KEY      = "AI_Log"       # 'enabled' or 'paused'
META_DIR_KEY       = "AI_LogDir"    # folder name of the log beside the file
LOG_OBJECT_NAME    = "AI_ProjectLog"  # the VarSet holding durable state

# log_001.md ... log_999.md, and nothing else. A loose slice such as f[4:7]
# reads log_1234.md as chapter 123 and writes into the wrong file.
CHAPTER_RE = re.compile(r"^log_(\d{3})\.md$")


def now_iso():
    """Local timestamp with seconds, used on every log entry."""
    return _log_datetime.datetime.now().isoformat(timespec="seconds")


def trim(text, max_chars=MAX_LINE_CHARS):
    """Cut overly long text and say how much was dropped, so nothing is
    silently lost from the AI's point of view."""
    if len(text) <= max_chars:
        return text
    return text[:max_chars] + " ...[trimmed %d chars]" % (len(text) - max_chars)


# ----------------------------------------------------------------------------
# Document flag helpers. Meta is read, changed and assigned back as a whole
# dictionary; changing it in place does not register. Note that Meta is a
# MIRROR only -- Part 3 keeps the authority on a VarSet, because a Meta-only
# change does not mark the document modified and is lost on close.
# ----------------------------------------------------------------------------
def get_flag(doc):
    """Return 'enabled', 'paused' or None for a document."""
    return dict(doc.Meta).get(META_FLAG_KEY)


def set_flag(doc, state):
    """Write the logging state and the log folder name into the document."""
    meta = dict(doc.Meta)
    meta[META_FLAG_KEY] = state
    meta[META_DIR_KEY] = log_dir_name(doc)
    doc.Meta = meta


def log_dir_name(doc):
    """Folder name for this document's log, e.g. 'MyPart.ai_log'.

    Raises on an unsaved document rather than inventing a location: with
    FileName == "", basename("") is "" so the folder becomes ".ai_log", and
    dirname("") is "" so it lands in FreeCAD's working directory -- often an
    unwritable Program Files bin/. A hidden folder in the install directory
    is worse than a clear refusal.
    """
    if not getattr(doc, "FileName", ""):
        raise ValueError("this document has never been saved, so there is "
                         "nowhere beside it to put a log; save it first")
    stem = os.path.splitext(os.path.basename(doc.FileName))[0]
    return stem + LOG_SUFFIX


def log_dir_path(doc):
    """Full path of the log folder, beside the .FCStd file."""
    return os.path.join(os.path.dirname(doc.FileName), log_dir_name(doc))


# ----------------------------------------------------------------------------
# Background writer. The main thread only ever puts strings on a queue.
# This thread batches them and appends to the current chapter file. File
# I/O releases Python's GIL, so the writing can run on another core.
# ----------------------------------------------------------------------------
class LogWriter(threading.Thread):
    def __init__(self, folder):
        super().__init__(name="AI_ProjectLog_Writer", daemon=True)
        self.folder = folder
        # Bounded: a runaway print loop -- the very thing being logged --
        # outruns a 1 s flush, and an unbounded queue would grow until
        # FreeCAD died. Overflow is counted and reported, never silent.
        self.q = queue.Queue(maxsize=QUEUE_MAX)
        self._stop_evt = threading.Event()
        self._lock = threading.Lock()
        self.last_error = None      # read by the main thread; see _flush()
        self.dropped = 0
        # Done here, on the main thread, before the thread starts: a raise
        # from inside run() would have nowhere to go.
        os.makedirs(self.folder, exist_ok=True)
        self.chapter = self._latest_chapter_number()

    # -- chapter files: log_001.md, log_002.md, ... -------------------------
    def chapter_path(self, n=None):
        # `n or self.chapter` would swallow n == 0.
        n = self.chapter if n is None else n
        return os.path.join(self.folder, "log_%03d.md" % n)

    def _latest_chapter_number(self):
        """Resume the newest chapter, stepping past it if it is already full."""
        nums = []
        if os.path.isdir(self.folder):
            for f in os.listdir(self.folder):
                m = CHAPTER_RE.match(f)
                if m:
                    nums.append(int(m.group(1)))
        n = max(nums) if nums else 1
        try:
            if os.path.getsize(self.chapter_path(n)) > CHAPTER_MAX_BYTES:
                n += 1
        except OSError:
            pass
        return n

    # -- public API used from the main thread -------------------------------
    def put(self, text):
        """Queue text for writing. Never blocks FreeCAD."""
        try:
            self.q.put_nowait(text)
        except queue.Full:
            self.dropped += 1

    def flush_now(self, fsync=True):
        """Force a write from the main thread. Used at checkpoints: atexit
        does not run on a hard crash, so the entries that matter most for a
        handover are the ones to get onto the platter immediately."""
        self._flush(fsync=fsync)

    def stop(self):
        """Ask the thread to flush everything and exit."""
        self._stop_evt.set()
        self.join(timeout=5)
        self._flush()               # belt and braces if the join timed out

    # -- thread body --------------------------------------------------------
    def run(self):
        # wait() returns the instant stop is set, rather than sleeping out the
        # whole interval first and making stop() hang for up to a second.
        while not self._stop_evt.wait(FLUSH_INTERVAL_S):
            self._flush()
        self._flush()               # final flush on stop

    def _flush(self, fsync=False):
        """Drain the queue and append in one write; roll the chapter if full."""
        with self._lock:            # flush_now() runs on the main thread
            parts = []
            while True:
                try:
                    parts.append(self.q.get_nowait())
                except queue.Empty:
                    break
            dropped, self.dropped = self.dropped, 0
            if dropped:
                parts.append("\n**%s** | note\n\n%d entries were dropped: the "
                             "queue hit its %d-entry ceiling.\n"
                             % (now_iso(), dropped, QUEUE_MAX))
            if not parts:
                return
            try:
                path = self.chapter_path()
                with open(path, "a", encoding="utf-8") as fh:
                    fh.write("".join(parts))
                    if fsync:
                        fh.flush()
                        os.fsync(fh.fileno())
                # Roll AFTER the write, so a chapter cannot overshoot
                # CHAPTER_MAX_BYTES by a whole batch -- and a batch is however
                # much arrived in a second, which has no ceiling of its own.
                if os.path.getsize(path) > CHAPTER_MAX_BYTES:
                    self.chapter += 1
                self.last_error = None
            except Exception as exc:
                # NEVER touch App.Console from here. It is wired to the Report
                # view, a Qt widget on the GUI thread, and Part 2 wraps
                # PrintWarning -- so a warning raised here would be captured,
                # re-queued, fail to write again, and grow the log by one
                # warning per second for as long as FreeCAD stayed open.
                # The main thread reads last_error and reports it once.
                self.last_error = str(exc)

from PySide6 import QtCore, QtGui, QtWidgets

FENCE = "`" * 3

# One Part::Box plus one Length edit fires seven slotChangedObject calls.
# These are the properties that carry no information for a reader.
SKIP_OBJ_PROPS = {"Shape", "_ElementMapVersion", "ElementMapVersion",
                  "AttachmentSupport"}

# Fired by every save. 'Meta' is here because our own flag write triggers
# BeforeChangeDocument:Meta -> ChangedDocument:Meta, which would log itself.
# 'FileName' is deliberately NOT skipped: a Save As moves where the log
# belongs, and _LogObserver acts on it.
SKIP_DOC_PROPS = {"LastModifiedDate", "LastModifiedBy", "TransientDir",
                  "Uid", "Label", "Meta"}

# How much of the log to carry inside the .FCStd. The whole thing is
# unbounded; a document that grows by tens of MB on every save is a bug the
# operator would feel long before they read the log.
EMBED_MAX_BYTES = 2_000_000

# Set true by the atexit hook. Qt may already be torn down by then, so
# teardown skips every widget and timer call.
_SHUTTING_DOWN = False


def trim_block(text, max_lines=MAX_BLOCK_LINES):
    """Cut an over-long block and say how many lines were dropped."""
    lines = text.splitlines()
    if len(lines) <= max_lines:
        return text
    return ("\n".join(lines[:max_lines])
            + "\n...[trimmed %d lines]" % (len(lines) - max_lines))


# ----------------------------------------------------------------------------
# Re-entrancy guard. Thread-local: the hooks fire on the GUI thread, the
# writer runs on its own. Every hook checks it, so nothing the logger itself
# emits is captured and fed back in.
# ----------------------------------------------------------------------------
_guard = threading.local()


def _busy():
    return getattr(_guard, "on", False)


class _Busy:
    def __enter__(self):
        _guard.on = True

    def __exit__(self, *exc):
        _guard.on = False
        return False            # never swallow the caller's exception


# ----------------------------------------------------------------------------
# The hook broker.
#
# App.Console, sys.stdout/stderr and the Python console widget are
# PROCESS-WIDE; the logs are per-document. 0.0.03 installed a set of hooks per
# logger, which was measured to do two wrong things: one console message was
# written into every open document's log, and stopping the first logger
# restored what IT had seen as the original -- really the second logger's
# wrapper -- so the second went deaf to the console while still looking
# healthy. One broker owns the hooks, installs them once, and routes each
# message to a single log.
# FreeCAD's own stdout/stderr redirector types. Temporary instances of these
# (one per Macro > Execute run) must never be wrapped -- see verify().
_FC_REDIRECTORS = ("OutputStdout", "OutputStderr",
                   "PythonStdout", "PythonStderr")
# ----------------------------------------------------------------------------
class _HookBroker:

    def __init__(self):
        self._subs = []
        self._installed = False
        self._orig_console = {}
        self._orig_stdout = None
        self._orig_stderr = None
        self._pc = None
        self._pc_prev = ""
        # 0.0.05: a hook that swallows its own failures turns into a log that
        # quietly stops recording. Count them and let the panel say so.
        self.hook_errors = 0
        self.last_hook_error = None
        # The tee objects we installed, so verify() can tell ours from a
        # host's replacement by identity rather than by type.
        self._tee = {}
        # How many times a host swapped stdout/stderr out from under us.
        # Counted, not hidden: a silent re-attach would make the defect it
        # recovers from invisible again.
        self.reattached = 0
        self.last_reattach = None
        # What we actually put on App.Console, so uninstall can check that it
        # is still ours before handing the original back.
        self._installed_fns = {}
        # Streams present at install (safe to re-wrap later) and the FreeCAD
        # temporary redirectors verify() deliberately did not wrap.
        self._install_real = {}
        self._last_foreign = {}
        self.foreign_left_alone = 0

    # -- membership ---------------------------------------------------------
    def subscribe(self, log):
        if log not in self._subs:
            self._subs.append(log)
        if not self._installed:
            self._install()

    def unsubscribe(self, log):
        if log in self._subs:
            self._subs.remove(log)
        if not self._subs and self._installed:
            self._uninstall()

    # -- routing ------------------------------------------------------------
    def _target(self):
        """The log that should own process-wide output: the active document's.

        A print() carries no document, so the active document is the only
        honest attribution available. Writing it to every open log, as 0.0.03
        did, makes each log claim work that happened once.
        """
        # 0.0.05: doc.Name was outside the guard. App.ActiveDocument can
        # hand back a proxy whose C++ object is gone, and reading .Name on
        # one raises -- inside a hook that FreeCAD's whole console goes
        # through.
        try:
            doc = App.ActiveDocument
            if doc is None:
                return None
            return LOGS.get(doc.Name)
        except BaseException:
            return None

    def _emit(self, kind, text, fenced=True):
        """Route one captured message. MUST NOT raise, ever.

        Everything downstream of this method is called from inside
        App.Console.Print* and from inside print(). If it raises, then every
        console call and every print() in the FreeCAD process raises with it
        -- including the ones the AI Bridge uses to report its own errors,
        which is how a Bridge goes zombie while its status file still reads
        healthy (seen 2026-11-07, fixed on the Bridge side in 3.4.7). Being
        total here is not defensive style; it is the contract of installing a
        process-wide hook.
        """
        try:
            # Two identity checks. Console output still reaches us when
            # stdout has been swapped away, so this is the path that heals
            # print() capture for a headless agent with no panel polling.
            self.verify()
            log = self._target()
            if log is not None:
                log.entry(kind, text, fenced=fenced)
        except BaseException as exc:
            try:
                self.hook_errors += 1
                self.last_hook_error = "%s: %s" % (type(exc).__name__, exc)
            except BaseException:
                pass

    # -- surviving a host that owns stdout too -----------------------------
    def verify(self):
        """Re-attach any stream a host swapped out from under us.

        The AI Bridge replaces sys.stdout with a per-command StringIO and
        restores it in a finally (001_AI_Bridge_3.4.8, _execute_command).
        Whichever side installed second wins, and since an agent starts this
        logger from inside a Bridge command, the side that loses is this one.

        Re-wrapping whatever is there now is safe in both directions: if the
        host restores its own saved stream afterwards, that stream is our
        earlier tee, which is still correct. Never raises.
        """
        if not self._installed:
            return
        try:
            for attr, label in (("stdout", "stdout"), ("stderr", "stderr")):
                cur = getattr(sys, attr, None)
                if cur is None or cur is self._tee.get(attr):
                    continue
                if isinstance(cur, _HookBroker._Tee) and cur._broker is self:
                    # Our own tee, re-made by an earlier verify(). Adopt it.
                    self._tee[attr] = cur
                    continue
                # A FreeCAD redirector we did not find at install is a
                # TEMPORARY one: Macro > Execute swaps in a fresh
                # OutputStdout/OutputStderr for the length of one macro and
                # frees it afterwards. A macro that opens a dialog spins the
                # event loop, the panel's 800 ms poll lands here mid-macro,
                # and wrapping that stream left a tee pointing at freed C++
                # memory: "Access violation" on every poll from then on
                # (FC 27.1, 2026-11-12, 163_Add_Conventional_Coordinates run
                # with the Bridge connected). Leave it alone; FreeCAD puts
                # our tee back itself when the macro ends.
                if (type(cur).__name__ in _FC_REDIRECTORS
                        and cur is not self._install_real.get(attr)):
                    if id(cur) != self._last_foreign.get(attr):
                        self._last_foreign[attr] = id(cur)
                        self.foreign_left_alone += 1
                    continue
                tee = _HookBroker._Tee(self, label, cur)
                self._tee[attr] = tee
                setattr(sys, attr, tee)
                self.reattached += 1
                self.last_reattach = (
                    "sys.%s was replaced by %s (a host swapping streams per "
                    "command, e.g. the AI Bridge); re-attached, but anything "
                    "printed in between is not in this log"
                    % (attr, type(cur).__name__))
        except BaseException as exc:
            try:
                self.hook_errors += 1
                self.last_hook_error = "%s: %s" % (type(exc).__name__, exc)
            except BaseException:
                pass

    # -- install / uninstall, exactly once ---------------------------------
    def _install(self):
        for name, label in (("PrintMessage", "console.message"),
                            ("PrintWarning", "console.warning"),
                            ("PrintError",   "console.error"),
                            ("PrintLog",     "console.log")):
            orig = getattr(App.Console, name)
            self._orig_console[name] = orig

            def hooked(text, *a, _orig=orig, _label=label, **kw):
                # _emit is total, but this call is still wrapped: FreeCAD's
                # own console must work even if this file is later edited
                # badly. The original is called whatever happens.
                try:
                    self._emit(_label, text)
                except BaseException:
                    pass
                return _orig(text, *a, **kw)

            setattr(App.Console, name, hooked)
            self._installed_fns[name] = hooked

        self._orig_stdout, self._orig_stderr = sys.stdout, sys.stderr
        self._install_real = {"stdout": sys.stdout, "stderr": sys.stderr}
        self._tee["stdout"] = _HookBroker._Tee(self, "stdout",
                                               self._orig_stdout)
        self._tee["stderr"] = _HookBroker._Tee(self, "stderr",
                                               self._orig_stderr)
        sys.stdout = self._tee["stdout"]
        sys.stderr = self._tee["stderr"]

        self._install_gui_echo()
        self._installed = True

    def _uninstall(self):
        # 0.0.05: restore by identity. 0.0.04 put the original back
        # unconditionally, so if anything else patched App.Console after us,
        # our teardown silently threw that patch away and replaced it with a
        # function captured before it existed -- the same mis-ordered-restore
        # bug the broker was built to remove, just one level up. If the
        # attribute is no longer the wrapper we installed, someone else owns
        # it now: leave it alone and say so.
        for name, orig in self._orig_console.items():
            mine = self._installed_fns.get(name)
            try:
                current = getattr(App.Console, name, None)
                if mine is not None and current is not mine:
                    self.hook_errors += 1
                    self.last_hook_error = (
                        "App.Console.%s was replaced by something else while "
                        "logging was running; left as found rather than "
                        "overwritten" % name)
                    continue
                setattr(App.Console, name, orig)
            except BaseException:
                pass
        self._orig_console.clear()
        self._installed_fns.clear()
        # Identity, not isinstance: after a re-attach the live tee is a
        # different object from the one install() made, and the only safe
        # thing to hand back is the stream that tee wraps.
        for attr in ("stdout", "stderr"):
            tee = self._tee.get(attr)
            cur = getattr(sys, attr, None)
            if tee is not None and cur is tee:
                setattr(sys, attr, tee._real)
            elif isinstance(cur, _HookBroker._Tee) and cur._broker is self:
                setattr(sys, attr, cur._real)
        self._tee.clear()
        if self._pc is not None and not _SHUTTING_DOWN:
            try:
                self._pc.textChanged.disconnect(self._on_py_console)
            except (RuntimeError, TypeError):
                pass
        self._pc = None
        self._pc_prev = ""
        self._installed = False

    # -- hook 2: print() and tracebacks ------------------------------------
    class _Tee:
        """Writes to the log AND to whatever FreeCAD had there before.
        FreeCAD already owns stdout (RedirectPythonStdout is True), so
        replacing instead of teeing would silence the Report view."""

        def __init__(self, broker, label, real):
            self._broker, self._label, self._real = broker, label, real

        def write(self, s):
            # Guarded separately from _emit: this is the body of every
            # print() in the process, including the ones inside other
            # people's exception handlers.
            try:
                if s and s.strip():
                    self._broker._emit(self._label, s)
            except BaseException:
                pass
            try:
                return self._real.write(s)
            except BaseException:
                return len(s or "")

        def flush(self):
            try:
                self._real.flush()
            except BaseException:
                pass

        def isatty(self):
            return False

        @property
        def encoding(self):
            return getattr(self._real, "encoding", "utf-8")

    # -- hook 3: GUI commands, as echoed into the Python console -----------
    def _install_gui_echo(self):
        # Headless FreeCADCmd still imports FreeCADGui, but the module is a
        # stub with no getMainWindow, and a module is always truthy.
        if not hasattr(Gui, "getMainWindow"):
            return
        mw = Gui.getMainWindow()
        if mw is None:
            return
        # QPlainTextEdit is in QtWidgets under Qt6, not QtGui, and
        # findChild(QWidget, ...) would return the QDockWidget.
        w = mw.findChild(QtWidgets.QPlainTextEdit, "Python console")
        if w is None:
            return
        self._pc = w
        self._pc_prev = w.toPlainText()
        w.textChanged.connect(self._on_py_console)

    def _on_py_console(self):
        if _busy() or self._pc is None:
            return
        try:
            txt = self._pc.toPlainText()
        except BaseException:
            return
        prev = self._pc_prev
        if txt.startswith(prev):
            fresh = txt[len(prev):]
        else:
            # Either the operator cleared the console, or FreeCAD trimmed the
            # scrollback from the top. 0.0.03 treated both as "cleared" and
            # resynced, losing everything in between in silence. Recover what
            # we can by finding the old tail, and SAY what went missing.
            # Try progressively shorter tails: a single fixed window is no
            # use, because the amount FreeCAD trims is not bounded by it.
            pos, tail = -1, ""
            for n in (4000, 2000, 1000, 500, 200, 80, 30):
                if n > len(prev):
                    continue
                cand = prev[-n:]
                p = txt.rfind(cand)
                if p >= 0:
                    pos, tail = p, cand
                    break
            if pos >= 0:
                fresh = txt[pos + len(tail):]
                self._emit("note",
                           "Python console history was trimmed or cleared; "
                           "about %d characters are no longer visible. "
                           "Commands echoed before that point are not in this "
                           "log." % max(0, len(prev) - pos - len(tail)),
                           fenced=False)
            else:
                fresh = ""
                self._emit("note",
                           "Python console was cleared; an unknown number of "
                           "echoed commands were lost from this log.",
                           fenced=False)
        self._pc_prev = txt
        lines = [ln for ln in fresh.splitlines()
                 if ln.strip() and ln.strip() != ">>>"]
        if lines:
            self._emit("command", "\n".join(lines))


BROKER = _HookBroker()


# ----------------------------------------------------------------------------
# The observer. Two-phase, as Rule 17 requires: slotChangedObject fires DURING
# the recompute, so it only sets flags; slotRecomputedDocument fires after it,
# and a 50 ms single-shot timer gets us fully out of the callback stack.
# ----------------------------------------------------------------------------
class _LogObserver:
    def __init__(self, log):
        self._log = log
        self._dirty = False
        self._tag = None          # 'undo' / 'redo' for this batch
        self._tx = None           # the gesture's own label, if FreeCAD gave one
        self._timer = QtCore.QTimer()
        self._timer.setSingleShot(True)
        self._timer.setInterval(50)
        self._timer.timeout.connect(self._fire)

    def _mine(self, doc):
        return getattr(doc, "Name", None) == self._log.doc_name

    # -- phase 1: flag only, never act --------------------------------------
    def slotChangedObject(self, obj, prop):
        if _busy() or prop in SKIP_OBJ_PROPS:
            return
        try:
            if not self._mine(obj.Document):
                return
            name = obj.Name
        except BaseException:
            return      # already deleted: a DeletedObject is followed by one
                        # more ChangedObject for AttachmentSupport
        self._log.changed.setdefault(name, set()).add(prop)
        self._dirty = True

    def slotChangedDocument(self, doc, prop):
        if _busy() or not self._mine(doc):
            return
        if prop == "FileName":
            # A Save As moves where the log belongs. 0.0.03 froze the writer's
            # folder at construction, so entries kept going to the old folder
            # while the panel and _RESUME.md showed the new path.
            self._log.retarget()
            return
        if prop in SKIP_DOC_PROPS:
            return
        self._log.doc_changed.add(prop)
        self._dirty = True

    # Creations and deletions are BUFFERED, not written on the spot. Measured
    # slot order for an undo on 26.3:
    #     slotDeletedObject -> slotUndoDocument -> slotRecomputedDocument
    # so the effect arrives BEFORE the notification and there is no
    # slotBeforeUndoDocument to lean on. Writing immediately is what made
    # 0.0.03 log an undo as a deliberate "removed Box". Buffering until the
    # recompute means the whole batch is written once the tag is known.
    def slotCreatedObject(self, obj):
        if _busy():
            return
        try:
            if not self._mine(obj.Document):
                return
            self._log.created.append("%s (%s)" % (obj.Name, obj.TypeId))
            self._dirty = True
        except BaseException:
            pass

    def slotDeletedObject(self, obj):
        if _busy():
            return
        try:
            if not self._mine(obj.Document):
                return
            self._log.removed.append(obj.Name)
            self._dirty = True
        except BaseException:
            pass

    # -- the operator's own words ------------------------------------------
    # slotOpenTransaction carries the label FreeCAD gave the gesture --
    # "make a box", "Paste", "Change Length". That is the closest thing to
    # intent available, and far more use to a resuming agent than a list of
    # property deltas.
    def slotOpenTransaction(self, doc, name):
        if _busy() or not self._mine(doc):
            return
        self._tx = name or None

    # -- undo / redo --------------------------------------------------------
    def _suffix(self):
        return "" if self._tag is None else " (%s)" % self._tag

    def slotUndoDocument(self, doc):
        if _busy() or not self._mine(doc):
            return
        self._tag = "undo"
        self._dirty = True

    def slotRedoDocument(self, doc):
        if _busy() or not self._mine(doc):
            return
        self._tag = "redo"
        self._dirty = True

    # -- phase 2: recompute is over, doc.recompute() works again ------------
    def slotRecomputedDocument(self, doc):
        if not self._dirty or not self._mine(doc):
            return
        self._dirty = False
        if QtCore.QCoreApplication.instance() is None:
            # No event loop (FreeCADCmd): a QTimer never fires, so every
            # pending change is dropped in silence. Writing now is safe --
            # the recompute has finished and _fire() never recomputes.
            self._fire()
        else:
            self._timer.start()

    def _fire(self):
        """Write one coherent batch for one operator gesture: what it was
        called, whether it was an undo, and what it did."""
        log = self._log
        created, removed = log.created, log.removed
        changed, docprops = log.changed, log.doc_changed
        log.created, log.removed = [], []
        log.changed, log.doc_changed = {}, set()
        suffix = self._suffix()
        tx, self._tx = self._tx, None
        self._tag = None

        if tx and (created or removed or changed or docprops):
            log.entry("action" + suffix, tx, fenced=False)
        for item in created:
            log.entry("added" + suffix, item)
        for item in removed:
            log.entry("removed" + suffix, item)
        for name in sorted(changed):
            log.entry("changed" + suffix, "%s: %s"
                      % (name, ", ".join(sorted(changed[name]))))
        if docprops:
            log.entry("document" + suffix, ", ".join(sorted(docprops)))

    # -- saves and closes ---------------------------------------------------
    def slotStartSaveDocument(self, doc, filename):
        # Embed BEFORE the bytes are written, so the copy travels with THIS
        # save. Doing it after would mark the document modified again the
        # instant the operator saved it.
        if _busy() or not self._mine(doc):
            return
        try:
            self._log.embed()
        except BaseException:
            pass

    def slotFinishSaveDocument(self, doc, filename):
        if _busy() or not self._mine(doc):
            return
        self._log.checkpoint("saved %s" % filename)

    def slotDeletedDocument(self, doc):
        # 0.0.03 left the logger installed on a document that no longer
        # existed: the final checkpoint failed silently because
        # App.getDocument() raises, so the log just stopped mid-sentence.
        if not self._mine(doc):
            return
        try:
            self._log.stop(reason="the document was closed")
        except BaseException:
            pass
        LOGS.pop(self._log.doc_name, None)


# ----------------------------------------------------------------------------
# One logger per document. Owns the writer; the hooks belong to the broker.
# ----------------------------------------------------------------------------
class ProjectLog:

    def __init__(self, doc):
        self.doc_name = doc.Name
        self.folder = log_dir_path(doc)
        self.writer = LogWriter(self.folder)
        self.writer.start()
        self.changed = {}
        self.doc_changed = set()
        self.created = []
        self.removed = []
        self._installed = False
        self._obs = None

    # -- one entry ----------------------------------------------------------
    def entry(self, kind, text, fenced=False):
        """Queue one Markdown entry. Any thread; never raises."""
        if _busy():
            return
        with _Busy():
            try:
                body = trim(trim_block(str(text).rstrip("\n")))
                if fenced:
                    body = FENCE + "text\n" + body + "\n" + FENCE
                self.writer.put("\n**%s** | %s\n\n%s\n"
                                % (now_iso(), kind, body))
            except BaseException:
                pass

    # -- Save As ------------------------------------------------------------
    def retarget(self):
        """Follow a Save As to the new location, leaving a trail both ways."""
        try:
            doc = App.getDocument(self.doc_name)
            new_folder = log_dir_path(doc)
        except BaseException:
            return
        if os.path.normcase(new_folder) == os.path.normcase(self.folder):
            return
        old_folder, old_writer = self.folder, self.writer
        self.entry("note", "this document was saved as a new file; logging "
                           "continues in %s" % new_folder, fenced=False)
        try:
            old_writer.stop()
        except BaseException:
            pass
        self.folder = new_folder
        self.writer = LogWriter(new_folder)
        self.writer.start()
        self.entry("note", "continued from %s" % old_folder, fenced=False)

    # -- the embedded copy --------------------------------------------------
    def embed(self):
        """Carry the log inside the .FCStd, capped. Returns bytes embedded."""
        return embed_log(self)

    # -- checkpoints --------------------------------------------------------
    def checkpoint(self, why):
        try:
            doc = App.getDocument(self.doc_name)
            names = sorted(o.Name for o in doc.Objects)
        except BaseException:
            return
        digest = hashlib.sha1("|".join(names).encode("utf-8")).hexdigest()[:12]
        self.entry("checkpoint",
                   "%s\n- objects: %d\n- tree: %s\n- fingerprint: %s"
                   % (why, len(names), ", ".join(names[:40]), digest))
        # Get the checkpoint onto the platter now. The writer is a daemon
        # thread, so a hard crash kills it without a final flush, and atexit
        # does not run either.
        try:
            self.writer.flush_now()
        except BaseException:
            pass

    # -- lifecycle ----------------------------------------------------------
    def install(self):
        if self._installed:
            return
        self._installed = True
        self._obs = _LogObserver(self)
        App.addDocumentObserver(self._obs)
        BROKER.subscribe(self)
        self.checkpoint("logging started")

    def stop(self, reason="logging stopped"):
        if not self._installed:
            return
        self._installed = False
        self.checkpoint(reason)
        BROKER.unsubscribe(self)
        if self._obs is not None:
            try:
                App.removeDocumentObserver(self._obs)
            except BaseException:
                pass
            if not _SHUTTING_DOWN:
                try:
                    self._obs._timer.stop()   # Rule 17: a started timer fires
                except (RuntimeError, TypeError):
                    pass
            self._obs = None
        self.writer.stop()


# ----------------------------------------------------------------------------
# The registry lives on the App module, not in macro globals, because macro
# globals do not survive a re-run but the observers and the wrapped console
# functions do.
# ----------------------------------------------------------------------------
_REG_KEY = "_ai_project_log_registry"
LOGS = getattr(App, _REG_KEY, None)
if LOGS is None:
    LOGS = {}
    setattr(App, _REG_KEY, LOGS)


def purge_all():
    """Tear down everything a previous run of this macro left installed."""
    for log in list(LOGS.values()):
        try:
            log.stop()
        except BaseException:
            pass
    LOGS.clear()
    try:
        BROKER._subs = []
        if BROKER._installed:
            BROKER._uninstall()
    except BaseException:
        pass


def _at_exit():
    # Qt is being torn down around us: touching a widget or timer here is a
    # known way to crash on exit, so teardown skips all of it.
    global _SHUTTING_DOWN
    _SHUTTING_DOWN = True
    try:
        purge_all()
    except BaseException:
        pass


# daemon=True means the interpreter kills the writer without running its final
# flush, so up to FLUSH_INTERVAL_S of entries -- including the last thing the
# operator did -- would vanish. This covers a clean exit; checkpoints fsync
# for the rest, since atexit does not run on a hard crash.
atexit.register(_at_exit)


def start_for(doc):
    """Begin logging one document, replacing any logger already on it."""
    old = LOGS.pop(doc.Name, None)
    if old is not None:
        try:
            old.stop()
        except BaseException:
            pass
    log = ProjectLog(doc)
    LOGS[doc.Name] = log      # registered BEFORE install, so the broker's
    log.install()             # _target() can already find it
    return log

import glob

STATE_PROP  = "LogState"
DIR_PROP    = "LogDir"
COPY_PROP   = "LogCopy"
RESUME_NAME = "_RESUME.md"
PROP_GROUP  = "AI_ProjectLog"

# name, type, tooltip. Declared in one place so migration and creation
# cannot drift apart.
LOG_PROPS = (
    (STATE_PROP, "App::PropertyString", "enabled, paused or off"),
    (DIR_PROP,   "App::PropertyString", "log folder name, beside the .FCStd"),
    (COPY_PROP,  "App::PropertyFileIncluded",
     "copy of the log, carried inside the .FCStd"),
)


def _ensure_props(obj):
    """Add any property this version expects but the document lacks.

    A FeaturePython-style one-shot create is why a property added in a later
    version never reaches a document saved by an earlier one (Rule 65): the
    constructor does not run again on load. Returns the names added.
    """
    added = []
    for name, kind, doc_str in LOG_PROPS:
        if name not in obj.PropertiesList:
            obj.addProperty(kind, name, PROP_GROUP, doc_str)
            added.append(name)
    return added


def _hide_from_tree(obj):
    """Keep the bookkeeping object out of the operator's model tree (Rule 32).
    GUI-only: there is no ViewObject headless."""
    try:
        vo = getattr(obj, "ViewObject", None)
        if vo is not None and hasattr(vo, "ShowInTree"):
            vo.ShowInTree = False
    except BaseException:
        pass


def log_object(doc, create=False):
    """The App::VarSet carrying this document's logging state.

    Measured on 26.3: setting a VarSet property marks the document modified,
    survives save/close/reopen with value and property group intact, and is
    not lost when the operator closes without saving. doc.Meta fails all
    three, which is why the authority lives here and not there.

    With create=True this also migrates an existing VarSet. It never mutates
    on a plain read: adding a property would mark the document modified
    behind the operator's back, and read_state() runs on a timer.
    """
    obj = doc.getObject(LOG_OBJECT_NAME)
    if obj is None:
        if not create:
            return None
        obj = doc.addObject("App::VarSet", LOG_OBJECT_NAME)
        obj.Label = "AI Project Log"
    if create:
        _ensure_props(obj)
        _hide_from_tree(obj)
    return obj


def read_state(doc):
    """'enabled', 'paused' or 'off'. Falls back to Part 1's Meta flag so a
    document flagged before Part 3 existed is still honoured."""
    obj = log_object(doc)
    if obj is not None:
        try:
            v = getattr(obj, STATE_PROP, "") or ""
        except BaseException:
            v = ""
        if v:
            return v
    try:
        return get_flag(doc) or "off"
    except BaseException:
        return "off"


def write_state(doc, state):
    """Authority is the VarSet; Part 1's Meta flag is mirrored so get_flag()
    stays honest for existing code. Wrapped in _Busy so creating the VarSet
    and writing Meta are not themselves logged."""
    with _Busy():
        obj = log_object(doc, create=True)
        setattr(obj, STATE_PROP, state)
        setattr(obj, DIR_PROP, log_dir_name(doc))
        try:
            set_flag(doc, state)
        except BaseException:
            pass
    return state


EMBED_HEADER = """<!-- Written by the Imagineering AI Bridge and carried
INSIDE this .FCStd. If you are an agent reading this, you have everything
you need: the geometry is in this same archive, and what follows is what
the model IS and how it came to be that way. Nothing beside the file is
required. -->

# This document, described

*What the model is now, then how it got here. Both travel inside the
.FCStd, so they survive being closed, moved, mailed and reopened.*

"""


def _embed_truthful(text, folder_name):
    """Rewrite pointers that are true on disk and false once embedded.

    The log says "the full inventory is in _RESUME.md" -- correct where
    it is written, beside the document. Inside the .FCStd, where the
    resume is now a section of this very file, it sends a resuming agent
    to a file that did not travel. The on-disk log is left alone; only
    the embedded copy is corrected.
    """
    swaps = [
        # written by the log, beside the document
        ("The full inventory is in %s." % RESUME_NAME,
         "The full inventory is the first section of this file, above."),
        ("The full inventory is in %s" % RESUME_NAME,
         "The full inventory is the first section of this file, above"),
        # written by the resume. True in the folder, false in here: it
        # sends a resuming agent to files that did not travel.
        ("Nothing is embedded in the .FCStd yet: it carries a copy "
         "only once the document has been saved while logging. These "
         "files beside it are the whole record.",
         "You are reading the embedded copy, inside the .FCStd itself."),
        ("A copy of the log as at the last save also rides inside the "
         ".FCStd, on the %s object, property %s."
         % (LOG_OBJECT_NAME, COPY_PROP),
         "You are reading that copy: it rides inside the .FCStd on the "
         "%s object, property %s." % (LOG_OBJECT_NAME, COPY_PROP)),
        ("Read the chapters in order. The newest entries are at the end of"
         + chr(10) +
         "the highest-numbered file.",
         "The history below is in order, oldest first; the newest entries"
         + chr(10) +
         "are at the end of this file."),
        ("## Chapters",
         "## Chapters  (names on the machine that wrote this; "
         "their contents are below)"),
    ]
    for old, new in swaps:
        text = text.replace(old, new)
    return text


def bundle_chapters(log, cap=EMBED_MAX_BYTES):
    """Everything a cold agent needs, in one file, for embedding.

    Order matters: the RESUME first, because it says what the model is
    right now, then the history of how it got there. An agent that reads
    only the top still knows what it is looking at.

    The resume is never capped -- it is the most useful part and much the
    smaller. Only the history is trimmed, and the TAIL is kept, because
    recent work is what a resuming agent needs.
    """
    folder = log.writer.folder
    pieces = [EMBED_HEADER]

    resume = os.path.join(folder, RESUME_NAME)
    if os.path.isfile(resume):
        try:
            pieces.append("<!-- %s, included in full -->\n\n" % RESUME_NAME)
            pieces.append(open(resume, encoding="utf-8").read())
            pieces.append("\n\n---\n\n# How it got here\n")
        except BaseException:
            pass

    chapters = sorted(glob.glob(os.path.join(folder, "log_*.md")))
    body = []
    for c in chapters:
        body.append("\n\n<!-- %s -->\n\n" % os.path.basename(c))
        try:
            body.append(open(c, encoding="utf-8").read())
        except BaseException:
            pass
    history = "".join(body)
    if len(history) > cap:
        dropped = len(history) - cap
        history = ("<!-- the first %d characters of the history are not "
                   "embedded. The complete log is in %s on the machine "
                   "that wrote this file; it did NOT travel with the "
                   "document. What follows is the most recent %d "
                   "characters. -->\n\n"
                   % (dropped, os.path.basename(folder), cap)
                   + history[-cap:])
    pieces.append(history)

    text = _embed_truthful("".join(pieces), os.path.basename(folder))
    # nothing to say at all -- no resume and no chapters
    if not os.path.isfile(resume) and not chapters:
        return None, 0

    bundle = os.path.join(folder, "_embedded.md")
    with open(bundle, "w", encoding="utf-8") as out:
        out.write(text)
    return bundle, os.path.getsize(bundle)


def embed_log(log):
    """Carry the log inside the .FCStd via App::PropertyFileIncluded.

    Verified on 26.3: FreeCAD copies the file into the document's own
    transient cache, the property then points there rather than at the
    original, and the bytes round-trip identically through save/reopen.
    """
    doc = App.getDocument(log.doc_name)
    bundle, size = bundle_chapters(log)
    if bundle is None:
        return 0
    with _Busy():
        obj = log_object(doc, create=True)
        setattr(obj, COPY_PROP, bundle)
    return size


# ----------------------------------------------------------------------------
# Document inventory -- what is already in the model, before anyone touches it.
#
# The point of this macro is that an agent can pick a project up cold. A list
# of object names does not say what the thing IS, and an agent that cannot see
# the model will cheerfully put a 0.5 mm fillet on a bridge. So measure it
# first: how big it is, what it weighs where a density is actually stated,
# where its centre of gravity sits, which numbers are parametric and can be
# turned, and what is already broken.
#
# Everything here is read-only. Nothing recomputes, touches or writes a
# property: the inventory must never be the reason a document changed.
# ----------------------------------------------------------------------------
import math
import time

INVENTORY_BUDGET_S = 3.0        # wall clock for all shape reads together
INVENTORY_MAX_ROWS = 200        # rows per table in the report
_INV_TTL_S = 5.0                # one measurement serves resume + log entry

# Datum scaffolding. Measured on 26.3: App::Origin's lines and planes report
# extents of +/-1e100 and areas of 8e100, so folding them into a model
# bounding box makes the single most useful number in the whole report -- how
# big is this thing -- read 1e100 mm. They teach an agent nothing either.
_INV_SKIP_TYPES = frozenset((
    "App::Origin", "App::OriginGroup", "App::Line", "App::Plane",
    "App::Point",
))


def _inv_finite(*vals):
    """True only when every value is a real, finite number.

    Deliberately narrow about what it catches. 0.0.07 used a bare except
    here, and because math was imported in Part 1 rather than beside this
    code, a NameError was swallowed into "not finite": every length in the
    report printed as "?", every density came back None, and every solid was
    written up as "has solids but no usable volume". A document full of
    geometry reported as an empty one, with nothing to say a name was
    missing. A bug in this file has to be able to say so, so only the
    exceptions a strange OCCT value actually raises are caught.
    """
    for v in vals:
        try:
            if not math.isfinite(float(v)):
                return False
        except (TypeError, ValueError, OverflowError, AttributeError):
            return False
    return True


def _fmt_len(mm):
    """A length in the unit a person would use for something that size."""
    if not _inv_finite(mm):
        return "?"
    a = abs(float(mm))
    if a >= 1000000.0:
        return "%.3f km" % (mm / 1000000.0)
    if a >= 1000.0:
        return "%.3f m" % (mm / 1000.0)
    if a < 1.0:
        return "%.4f mm" % mm
    return "%.2f mm" % mm


def _fmt_vol(mm3):
    if not _inv_finite(mm3):
        return "?"
    v = float(mm3)
    if v >= 1e9:
        return "%.4f m3" % (v / 1e9)
    if v >= 1e6:
        return "%.1f cm3 (%.3f L)" % (v / 1000.0, v / 1e6)
    if v >= 1000.0:
        return "%.2f cm3" % (v / 1000.0)
    return "%.1f mm3" % v


def _fmt_mass(kg):
    if not _inv_finite(kg):
        return "?"
    v = float(kg)
    if v >= 1000.0:
        return "%.3f t" % (v / 1000.0)
    if v < 1.0:
        return "%.1f g" % (v * 1000.0)
    return "%.3f kg" % v


def _fmt_vec(v):
    try:
        if not _inv_finite(v.x, v.y, v.z):
            return "?"
        return "(%.2f, %.2f, %.2f)" % (v.x, v.y, v.z)
    except BaseException:
        return "?"


# -- density -----------------------------------------------------------------
try:
    _DENSITY_UNIT = App.Units.Quantity("1 kg/mm^3").Unit
except BaseException:
    _DENSITY_UNIT = None

# FreeCAD's unassigned placeholder, which is not a material anybody chose.
# Measured on 26.3: every Part feature starts with this card, its own
# Description reads "Generic material with density of 1", and its density is
# 1e-09 kg/mm^3 -- 1 kg/m^3, about the density of air. It answers
# hasPhysicalProperty('Density') with True, so it is indistinguishable from a
# real assignment unless it is named. Taking it at its word made this macro
# publish a centre of gravity, in bold, for a model with no materials on it.
_PLACEHOLDER_MATERIAL_UUIDS = frozenset((
    "7f9fd73b-50c9-41d8-b7b2-575a030c1eeb",       # 'Default'
))
_PLACEHOLDER_MATERIAL_NAMES = frozenset(("", "default", "none"))

# A plausibility band, as the third and last line of defence: should the
# placeholder's UUID and name both change upstream, a 1 kg/m^3 "material"
# must still not be multiplied by a volume and presented as a weight.
# Expanded polystyrene is about 15 kg/m^3 and osmium about 22 600; of the 222
# cards FreeCAD 26.3 ships, exactly one falls outside this band -- a card
# named 'None' whose density is 0 -- and not one is above it.
_DENSITY_MIN_KG_MM3 = 2.0e-9          # 2 kg/m^3
_DENSITY_MAX_KG_MM3 = 1.0e-4          # 100 000 kg/m^3


def _is_placeholder_material(mat):
    """True when this is FreeCAD's default card rather than a choice."""
    try:
        uuid = str(getattr(mat, "UUID", "") or "")
        if uuid in _PLACEHOLDER_MATERIAL_UUIDS:
            return True
        name = str(getattr(mat, "Name", "") or "").strip().lower()
        return name in _PLACEHOLDER_MATERIAL_NAMES
    except BaseException:
        return True


def _as_density(raw):
    """A stated density as kg/mm^3, or None when it has no usable unit.

    A bare number is refused on purpose. FreeCAD's own cards write
    '7.8e-06 kg/mm^3', and guessing the unit of a unitless 7850 is the
    difference between a 20 kg bracket and a 20 tonne one.
    """
    try:
        if isinstance(raw, bool) or isinstance(raw, (int, float)):
            return None
        q = App.Units.Quantity(str(raw))
        # Measured on 26.3: str(Quantity.Unit) is NEVER empty -- a
        # dimensionless quantity stringifies as 'Unit:  (0,0,...) [1]' -- so
        # testing it for emptiness rejects nothing. Compare the dimensions.
        if _DENSITY_UNIT is not None and q.Unit != _DENSITY_UNIT:
            return None
        val = q.getValueAs("kg/mm^3")     # raises on a unitless quantity
        val = float(getattr(val, "Value", val))
        return val if _inv_finite(val) and val > 0 else None
    except BaseException:
        return None


def _density_kg_mm3(obj):
    """(kg/mm^3, source) for this object, or (None, reason).

    Only a density FreeCAD actually holds counts. Volume is exact geometry;
    mass is volume x density, and a density nobody assigned is not a small
    inaccuracy -- it is a number that looks authoritative and is wrong.
    Assuming steel would be worse than saying nothing, so a missing density
    is reported as missing.

    Measured on 26.3: a Part feature carries ShapeMaterial, a full
    Materials.Material whose getPhysicalValue('Density') returns a quantity
    string like '7.8e-06 kg/mm^3' once a card has been assigned -- 222 of the
    shipped cards carry one. The FEM and Arch pattern instead puts a plain
    dict on obj.Material.
    """
    # The fallback reason, replaced by anything more specific found below.
    # It is a REASON and not a verdict: a placeholder card on ShapeMaterial
    # must not stop obj.Material being asked, which is where the FEM and
    # Arch pattern keeps a real density. 0.0.09 returned here and so never
    # looked, reporting "no material assigned" for objects that had one.
    reason = "no density assigned"
    for attr in ("ShapeMaterial", "Material"):
        mat = getattr(obj, attr, None)
        if mat is None:
            continue
        try:
            if not hasattr(mat, "hasPhysicalProperty"):
                continue
            if _is_placeholder_material(mat):
                reason = ("no material assigned; the object still carries "
                          "FreeCAD's 'Default' placeholder card")
                continue
            if not mat.hasPhysicalProperty("Density"):
                continue
            raw = mat.getPhysicalValue("Density")
            val = _as_density(raw)
            name = str(getattr(mat, "Name", "") or "unnamed")
            if val is None:
                reason = ("the '%s' card's density, %r, could not be read as "
                          "a density" % (name, raw))
                continue
            if not (_DENSITY_MIN_KG_MM3 <= val <= _DENSITY_MAX_KG_MM3):
                reason = ("the '%s' card gives a density of %.4g kg/m3, "
                          "which is not physically plausible, so it was not "
                          "used" % (name, val * 1.0e9))
                continue
            return val, "%s card '%s'" % (attr, name)
        except BaseException:
            pass
    mat = getattr(obj, "Material", None)
    if isinstance(mat, dict):
        for key in ("Density", "density"):
            if key in mat:
                val = _as_density(mat[key])
                if val is None:
                    return None, ("Material['%s'] is %r, which carries no "
                                  "unit, so it cannot be read as a density"
                                  % (key, mat[key]))
                if not (_DENSITY_MIN_KG_MM3 <= val <= _DENSITY_MAX_KG_MM3):
                    return None, ("Material['%s'] gives %.4g kg/m3, which is "
                                  "not physically plausible, so it was not "
                                  "used" % (key, val * 1.0e9))
                return val, "Material dict"
    return None, reason


# -- geometry ----------------------------------------------------------------
# Structure rather than parts. A populated one of these aggregates its
# children's shapes, so counting both the container and its children would
# double every assembly. The children are the parts; the container is where
# they sit.
_INV_CONTAINER_TYPES = frozenset((
    "App::Part", "App::DocumentObjectGroup", "App::LinkGroup",
    "Part::Compound",
))


def _inv_chain(obj):
    """The placement of the containers ABOVE this object.

    NOT obj.getGlobalPlacement(). Measured on 26.3, that includes the
    object's OWN placement, and obj.Shape already does too, so composing the
    two applies it twice: a part at (5, 0, 0) inside a container at
    (100, 0, 0) turned 90 degrees lands 5 mm from where the container's own
    solid says it is. Silent, and in the one number this section exists to
    get right.

    Verified against the container's Shape.Solids -- which ARE global -- to
    1e-14, for a nested App::Part chain and for a plain Group.
    """
    try:
        parent = obj.getParentGeoFeatureGroup()
        if parent is not None:
            return parent.getGlobalPlacement()
        return App.Placement()
    except BaseException:
        pass
    try:
        # Not every type has that method. Undoing the object's own placement
        # measured identically on both cases.
        return obj.getGlobalPlacement().multiply(obj.Placement.inverse())
    except BaseException:
        return App.Placement()


def _inv_container_of(obj):
    """The name of whatever this part sits in, or '' for a loose part."""
    try:
        for p in (getattr(obj, "InList", None) or ()):
            if getattr(p, "TypeId", "") in _INV_CONTAINER_TYPES:
                return str(getattr(p, "Label", None)
                           or getattr(p, "Name", ""))
    except BaseException:
        pass
    return ""


def _inv_consumed(obj, cache):
    """Is this object's shape swallowed by something that is not a container?

    A boolean's Base and Tool, and each PartDesign feature inside its Body,
    are consumed: they must be counted once, through the result. Containers
    are deliberately NOT consumers -- they are the structure, and their
    children are exactly what we want to count.
    """
    for p in (getattr(obj, "InList", None) or ()):
        if getattr(p, "TypeId", "") in _INV_CONTAINER_TYPES:
            continue
        if _inv_has_solids(p, cache):
            return True
    return False


def _inv_has_solids(obj, cache):
    """Does this object carry at least one solid? Cached, because the
    consumer test below asks the same question of the same objects again."""
    name = getattr(obj, "Name", None)
    if name is None:
        return False
    if name in cache:
        return cache[name]
    ok = False
    try:
        sh = getattr(obj, "Shape", None)
        ok = bool(sh is not None and not sh.isNull() and len(sh.Solids) > 0)
    except BaseException:
        ok = False
    cache[name] = ok
    return ok


def measure_solids(doc, budget_s=INVENTORY_BUDGET_S):
    """Measure every top-level solid in the document. Returns (rows, notes).

    "Top level" means no other shape-bearing object consumes it, so a
    boolean's Base and Tool, a PartDesign feature inside a Body and a part
    inside an App::Part are each measured once -- through whatever consumes
    them -- instead of being added to the total twice. Measured on 26.3: an
    App::Part reports its children's volume as its own, so counting both
    doubles the weight of every assembly.

    Centroids are read from shape.Solids, NOT from obj.Shape.CenterOfMass.
    For a part inside a moved App::Part the latter is the LOCAL centroid:
    measured on 26.3, Inner.Shape.CenterOfMass is (5, 10, 15) while the same
    solid reached through the container sits at (105, 10, 15). Reporting the
    local one puts the centre of gravity in the wrong place with nothing to
    show for it. Asking the shape directly is not an option either: a
    Compound has no CenterOfMass attribute at all, and neither has a Vertex.
    """
    t0 = time.time()
    rows, notes = [], []
    cache = {}
    over_budget = 0
    try:
        objs = list(doc.Objects)
    except BaseException:
        return rows, ["the document would not list its objects"]

    for obj in objs:
        if getattr(obj, "TypeId", "") in _INV_SKIP_TYPES:
            continue
        if time.time() - t0 > budget_s:
            over_budget += 1
            continue
        try:
            if getattr(obj, "TypeId", "") in _INV_CONTAINER_TYPES:
                continue                      # structure, not a part
            if not _inv_has_solids(obj, cache):
                continue
            if _inv_consumed(obj, cache):
                continue
            chain = _inv_chain(obj)
            sh = obj.Shape
            solids = sh.Solids
            vol = 0.0
            cx = cy = cz = 0.0
            lo = [None, None, None]
            hi = [None, None, None]
            bad = 0
            for sol in solids:
                try:
                    v = float(sol.Volume)
                    com = chain.multVec(sol.CenterOfMass)
                    if v <= 0 or not _inv_finite(v, com.x, com.y, com.z):
                        bad += 1
                        continue
                    vol += v
                    cx += com.x * v
                    cy += com.y * v
                    cz += com.z * v
                    # A rotated box cannot be transformed as a box, so carry
                    # the eight corners across and take their extent. Under
                    # rotation that is the usual axis-aligned over-estimate,
                    # which is what a bounding box is.
                    bb = sol.BoundBox
                    if _inv_finite(bb.XMin, bb.YMin, bb.ZMin,
                                   bb.XMax, bb.YMax, bb.ZMax):
                        for ix in (bb.XMin, bb.XMax):
                            for iy in (bb.YMin, bb.YMax):
                                for iz in (bb.ZMin, bb.ZMax):
                                    p = chain.multVec(App.Vector(ix, iy, iz))
                                    for i, c in enumerate((p.x, p.y, p.z)):
                                        lo[i] = (c if lo[i] is None
                                                 else min(lo[i], c))
                                        hi[i] = (c if hi[i] is None
                                                 else max(hi[i], c))
                except BaseException:
                    bad += 1
            if vol <= 0:
                notes.append("`%s` has solids but no usable volume, so it is "
                             "not counted" % obj.Name)
                continue
            dens, dsrc = _density_kg_mm3(obj)
            rows.append({
                "name": obj.Name,
                "label": getattr(obj, "Label", obj.Name),
                "container": _inv_container_of(obj),
                "type": getattr(obj, "TypeId", "?"),
                "solids": len(solids),
                "faces": len(sh.Faces),
                "volume": vol,
                "com": App.Vector(cx / vol, cy / vol, cz / vol),
                "bbox": (None if lo[0] is None
                         else (lo[0], lo[1], lo[2], hi[0], hi[1], hi[2])),
                "valid": bool(sh.isValid()),
                "density": dens,
                "density_src": dsrc,
                "mass": (vol * dens) if dens else None,
                "bad_solids": bad,
            })
            if bad:
                notes.append("`%s`: %d of its %d solids could not be measured"
                             % (obj.Name, bad, len(solids)))
        except BaseException as exc:
            notes.append("`%s` could not be measured (%s)"
                         % (getattr(obj, "Name", "?"), type(exc).__name__))
    if over_budget:
        notes.append("%d objects were left unmeasured: the %.1f s shape-"
                     "reading budget ran out. Every total below is of what "
                     "WAS measured, not of the whole model."
                     % (over_budget, budget_s))
    return rows, notes


def solid_totals(rows):
    """Volume, centroid, overall extent, and -- only where every solid has a
    stated density -- mass and a true centre of gravity.

    The distinction matters. A volume-weighted centroid is the centre of
    gravity ONLY if everything is the same material. Mix steel and foam and
    the real centre of gravity moves a long way from it, so a report that
    calls the volume centroid "the centre of gravity" is wrong in exactly the
    case where the answer matters.
    """
    out = {"count": len(rows), "volume": 0.0, "centroid": None,
           "mass": None, "cog": None, "with_density": 0,
           "without_density": 0, "bbox": None, "diagonal": None}
    if not rows:
        return out
    vol = vx = vy = vz = 0.0
    mass = mx = my = mz = 0.0
    lo = [None, None, None]
    hi = [None, None, None]
    for r in rows:
        v = r["volume"]
        vol += v
        vx += r["com"].x * v
        vy += r["com"].y * v
        vz += r["com"].z * v
        if r["density"]:
            out["with_density"] += 1
            m = r["mass"]
            mass += m
            mx += r["com"].x * m
            my += r["com"].y * m
            mz += r["com"].z * m
        else:
            out["without_density"] += 1
        bb = r["bbox"]
        if bb:
            for i in range(3):
                lo[i] = bb[i] if lo[i] is None else min(lo[i], bb[i])
                hi[i] = (bb[i + 3] if hi[i] is None
                         else max(hi[i], bb[i + 3]))
    out["volume"] = vol
    if vol > 0:
        out["centroid"] = App.Vector(vx / vol, vy / vol, vz / vol)
    if mass > 0:
        out["mass"] = mass
        if out["without_density"] == 0:
            out["cog"] = App.Vector(mx / mass, my / mass, mz / mass)
    if lo[0] is not None:
        out["bbox"] = (lo[0], lo[1], lo[2], hi[0], hi[1], hi[2])
        out["diagonal"] = math.sqrt(sum((hi[i] - lo[i]) ** 2
                                        for i in range(3)))
    return out


def measure_knobs(doc):
    """What an agent can actually turn: (aliases, bindings).

    A spreadsheet alias and an expression binding are the difference between
    an agent editing geometry by hand and driving the model the way it was
    built to be driven.
    """
    aliases, bindings = [], []
    for obj in (getattr(doc, "Objects", None) or ()):
        try:
            if getattr(obj, "TypeId", "") == "Spreadsheet::Sheet":
                for cell in (obj.getUsedCells() or ()):
                    try:
                        alias = obj.getAlias(cell)
                    except BaseException:
                        alias = None
                    if not alias:
                        continue
                    try:
                        val = obj.get(cell)
                    except BaseException:
                        val = "?"
                    aliases.append((obj.Name, alias, cell, str(val)[:60]))
            for prop, expr in (getattr(obj, "ExpressionEngine", None) or ()):
                bindings.append((obj.Name, str(prop), str(expr)[:90]))
        except BaseException:
            continue
    return aliases, bindings


def measure_health(doc):
    """Anything already wrong, so an agent does not mistake a fault it
    inherited for one it caused."""
    bad = []
    for obj in (getattr(doc, "Objects", None) or ()):
        try:
            flags = [s for s in (getattr(obj, "State", None) or ())
                     if s != "Up-to-date"]
            sh = getattr(obj, "Shape", None)
            if sh is not None:
                if sh.isNull():
                    if getattr(obj, "TypeId", "").startswith("Part"):
                        flags.append("empty shape")
                elif not sh.isValid():
                    flags.append("shape OCCT calls invalid")
            if flags:
                bad.append((obj.Name, getattr(obj, "TypeId", "?"),
                            ", ".join(flags)))
        except BaseException:
            continue
    return bad


def measure_census(doc):
    """Counts by type, and which modules the model implies. An agent that
    knows the model is Sketcher plus PartDesign writes different code from
    one guessing at Part primitives."""
    counts = {}
    modules = set()
    for obj in (getattr(doc, "Objects", None) or ()):
        try:
            t = getattr(obj, "TypeId", "?")
            counts[t] = counts.get(t, 0) + 1
            # Python features (Draft, Arch/BIM, StructureTools, FEM) all share
            # a generic TypeId; the Proxy's own module is what names them.
            proxy = getattr(obj, "Proxy", None)
            if proxy is not None:
                mod = (getattr(type(proxy), "__module__", "") or "")
                top = mod.split(".")[0]
                if top and top not in ("__main__", "builtins"):
                    modules.add(top)
        except BaseException:
            continue
    for t in list(counts):
        head = t.split("::")[0]
        if head and head != t:
            modules.add(head)
    return counts, sorted(modules)


# -- one measurement, two readers --------------------------------------------
# Without this cache, starting a logger measures a big assembly twice -- once
# for _RESUME.md and once for the opening log entry -- and pays the whole
# shape-reading budget over again. The TTL is deliberately short: a later
# checkpoint must re-measure, because by then the model has moved on.
_INV_CACHE = {"key": None, "t": 0.0, "rows": None, "tot": None, "notes": None}


def _measure_cached(doc, budget_s=INVENTORY_BUDGET_S):
    try:
        key = (doc.Name, len(doc.Objects))
    except BaseException:
        key = None
    if (key is not None and _INV_CACHE["key"] == key
            and (time.time() - _INV_CACHE["t"]) < _INV_TTL_S
            and _INV_CACHE["rows"] is not None):
        return _INV_CACHE["rows"], _INV_CACHE["tot"], _INV_CACHE["notes"]
    rows, notes = measure_solids(doc, budget_s=budget_s)
    tot = solid_totals(rows)
    _INV_CACHE.update(key=key, t=time.time(), rows=rows, tot=tot, notes=notes)
    return rows, tot, notes


# -- the report --------------------------------------------------------------
def _scale_advice(diag):
    """One sentence an agent can act on. The commonest way for an AI to ruin
    a model it cannot see is a feature three orders of magnitude the wrong
    size: a 0.5 mm fillet on a bridge, a 50 m extrusion on a bracket."""
    if not _inv_finite(diag):
        return ""
    if diag < 50:
        return ("This is a small part: features run from tenths of a "
                "millimetre to a few millimetres.")
    if diag < 1000:
        return ("This is a hand-sized to desk-sized part: features run from "
                "millimetres to tens of millimetres.")
    if diag < 20000:
        return ("This is furniture, machine or vehicle scale: features run "
                "from tens to hundreds of millimetres.")
    return ("This is building or site scale: features run from hundreds of "
            "millimetres to metres, and a millimetre-scale operation here is "
            "almost certainly a mistake.")


def _inv_doc_facts(doc):
    out = ["### The file", ""]
    for label, attr in (("document", "FileName"),
                        ("created", "CreationDate"),
                        ("last saved", "LastModifiedDate"),
                        ("created by", "CreatedBy"),
                        ("company", "Company"),
                        ("licence", "License"),
                        ("id", "Uid")):
        try:
            val = getattr(doc, attr, "") or ""
        except BaseException:
            val = ""
        if val:
            out.append("- %s: %s" % (label, val))
    try:
        if doc.isTouched():
            out.append("- FreeCAD reports unsaved changes. Opening a "
                       "document last saved by an older version sets this "
                       "by itself, so on its own it does not mean anyone "
                       "edited anything.")
        else:
            out.append("- no unsaved changes")
    except BaseException:
        pass
    return out + [""]


def _inv_scale(tot):
    out = ["### Size", ""]
    bb, diag = tot.get("bbox"), tot.get("diagonal")
    if bb is None:
        return out + ["Nothing with a measurable solid, so the model has no "
                      "size to report.", ""]
    return out + [
        "- extent: %s x %s x %s" % (_fmt_len(bb[3] - bb[0]),
                                    _fmt_len(bb[4] - bb[1]),
                                    _fmt_len(bb[5] - bb[2])),
        "- corner to corner: %s" % _fmt_len(diag),
        "- occupies %s to %s" % (_fmt_vec(App.Vector(bb[0], bb[1], bb[2])),
                                 _fmt_vec(App.Vector(bb[3], bb[4], bb[5]))),
        "",
        _scale_advice(diag),
        "",
    ]


def _inv_mass_cell(r):
    """The mass column. A dash where no material is assigned -- the section
    says that once, in bold, above the table, and repeating the sentence on
    every row pushed the numbers off the page on a real assembly. A density
    that WAS set but could not be used is unusual, so it stays visible."""
    if r["mass"]:
        return _fmt_mass(r["mass"])
    src = r.get("density_src", "")
    if "placeholder" in src or src == "no density assigned":
        return "-"
    return "- (%s)" % src


def _inv_mass(rows, tot, notes):
    out = ["### Weight and balance", ""]
    if not rows:
        return out + ["No solid was measured, so there is nothing to weigh.",
                      ""]
    out += ["- solids counted: %d" % tot["count"],
            "- total volume: %s" % _fmt_vol(tot["volume"])]
    if tot["centroid"] is not None:
        out.append("- centroid of volume: %s mm" % _fmt_vec(tot["centroid"]))
    if tot["cog"] is not None:
        out += ["- **total mass: %s**" % _fmt_mass(tot["mass"]),
                "- **centre of gravity: %s mm**" % _fmt_vec(tot["cog"]),
                "",
                "Every solid counted carries a stated density, so the mass "
                "and the centre of gravity are measured numbers rather than "
                "estimates."]
    elif tot["mass"]:
        out += ["",
                "**The centre of gravity cannot be given.** %d of the %d "
                "solids carry a density and %d do not, so the figures above "
                "are volume only. The %s accounted for by the materials that "
                "ARE set is a floor, not the weight of this model."
                % (tot["with_density"], tot["count"],
                   tot["without_density"], _fmt_mass(tot["mass"]))]
    else:
        out += ["",
                "**No mass, and no centre of gravity.** Not one solid in "
                "this document has a material with a density on it, and "
                "volume alone cannot be weighed. The centroid above is the "
                "centre of gravity only if the whole model turns out to be "
                "one material. To get a real weight, assign materials in "
                "FreeCAD and read this again."]
    out += ["", "Containers are not counted; the parts inside them are, so "
            "nothing is weighed twice. Centroids are global.", "",
            "| part | in | type | volume | centroid (mm) | mass |",
            "|---|---|---|---|---|---|"]
    for r in rows[:INVENTORY_MAX_ROWS]:
        out.append("| `%s` | %s | %s | %s | %s | %s |"
                   % (r["name"], r.get("container") or "-",
                      r["type"].split("::")[-1],
                      _fmt_vol(r["volume"]), _fmt_vec(r["com"]),
                      _inv_mass_cell(r)))
    if len(rows) > INVENTORY_MAX_ROWS:
        out += ["", "...and %d further solids, not listed."
                % (len(rows) - INVENTORY_MAX_ROWS)]
    rejected = [r for r in rows if r["density"] is None
                and ("not physically plausible" in r["density_src"]
                     or "could not be read" in r["density_src"])]
    if rejected:
        out += ["", "A material IS set on these, but its density was not "
                "usable, so they are counted as having none. If you expected "
                "them to be weighed, this is why they were not:"]
        for r in rejected[:INVENTORY_MAX_ROWS]:
            out.append("- `%s`: %s" % (r["name"], r["density_src"]))
    invalid = [r for r in rows if not r["valid"]]
    if invalid:
        out += ["", "OCCT calls these shapes invalid, so their numbers above "
                "should not be trusted: %s"
                % ", ".join("`%s`" % r["name"] for r in invalid)]
    if notes:
        out += [""] + ["- %s" % n for n in notes]
    return out + [""]


def _inv_knobs(doc):
    aliases, bindings = measure_knobs(doc)
    out = ["### What is parametric", ""]
    if not aliases and not bindings:
        return out + ["No spreadsheet aliases and no expression bindings: "
                      "nothing in this model is driven by a named value, so "
                      "changing it means editing geometry directly.", ""]
    if aliases:
        out += ["Named values. Setting one of these is how this model is "
                "meant to be changed.", "",
                "| sheet | alias | cell | value |", "|---|---|---|---|"]
        for sheet, alias, cell, val in aliases[:INVENTORY_MAX_ROWS]:
            out.append("| `%s` | `%s` | %s | %s |"
                       % (sheet, alias, cell, val))
        out.append("")
    if bindings:
        out += ["Properties already bound to an expression. Writing to one "
                "of these by hand will be overwritten on the next "
                "recompute.", "",
                "| object | property | expression |", "|---|---|---|"]
        for name, prop, expr in bindings[:INVENTORY_MAX_ROWS]:
            out.append("| `%s` | %s | `%s` |" % (name, prop, expr))
        out.append("")
    return out


def _inv_structure(doc):
    counts, modules = measure_census(doc)
    out = ["### Make-up", ""]
    if modules:
        out.append("- modules in play: %s" % ", ".join(modules))
    total = sum(counts.values())
    out.append("- objects: %d across %d types" % (total, len(counts)))
    ranked = sorted(counts.items(), key=lambda kv: (-kv[1], kv[0]))
    for t, n in ranked[:25]:
        out.append("  - %d x `%s`" % (n, t))
    if len(ranked) > 25:
        out.append("  - ...and %d further types" % (len(ranked) - 25))
    return out + [""]


def _inv_health(doc):
    bad = measure_health(doc)
    out = ["### State", ""]
    if not bad:
        return out + ["Every object is up to date with a valid shape. "
                      "Anything that breaks from here was caused by work "
                      "done after this point.", ""]
    out += ["%d objects are NOT clean. This is how the document was found, "
            "before any work in this session." % len(bad), "",
            "| object | type | what is wrong |", "|---|---|---|"]
    for name, typ, flags in bad[:INVENTORY_MAX_ROWS]:
        out.append("| `%s` | %s | %s |" % (name, typ, flags))
    return out + [""]


def inventory_markdown(doc, budget_s=INVENTORY_BUDGET_S):
    """The whole inventory as Markdown. Never raises: whatever could not be
    measured says so, and the rest is still written."""
    t0 = time.time()
    out = ["## What is in this document", "",
           "Measured from the geometry, read-only, at %s." % now_iso(), ""]
    try:
        rows, tot, notes = _measure_cached(doc, budget_s=budget_s)
        out += _inv_doc_facts(doc)
        out += _inv_scale(tot)
        out += _inv_mass(rows, tot, notes)
        out += _inv_knobs(doc)
        out += _inv_structure(doc)
        out += _inv_health(doc)
    except BaseException as exc:
        out += ["", "The inventory stopped early -- %s: %s. What is above it "
                "was measured; what is below it was not."
                % (type(exc).__name__, exc), ""]
    out += ["_Inventory read in %d ms. It changes nothing in the document._"
            % int((time.time() - t0) * 1000.0)]
    return "\n".join(out)


def inventory_summary(doc, budget_s=INVENTORY_BUDGET_S):
    """The same measurements, short enough for a log entry. An entry is
    trimmed at MAX_BLOCK_LINES lines, so the full report belongs in the
    resume file and this is only the headline."""
    try:
        rows, tot, notes = _measure_cached(doc, budget_s=budget_s)
    except BaseException as exc:
        return "the model could not be measured: %s: %s" % (
            type(exc).__name__, exc)
    counts, modules = measure_census(doc)
    aliases, bindings = measure_knobs(doc)
    bad = measure_health(doc)
    out = ["the document as it was found, before any work in this session:",
           "- objects: %d, modules: %s"
           % (sum(counts.values()), ", ".join(modules) or "none"),
           "- solids measured: %d, total volume %s"
           % (tot["count"], _fmt_vol(tot["volume"]))]
    if tot["diagonal"]:
        out.append("- size: %s x %s x %s, %s corner to corner"
                   % (_fmt_len(tot["bbox"][3] - tot["bbox"][0]),
                      _fmt_len(tot["bbox"][4] - tot["bbox"][1]),
                      _fmt_len(tot["bbox"][5] - tot["bbox"][2]),
                      _fmt_len(tot["diagonal"])))
    if tot["centroid"] is not None:
        out.append("- centroid of volume: %s mm" % _fmt_vec(tot["centroid"]))
    if tot["cog"] is not None:
        out.append("- mass %s, centre of gravity %s mm (every solid has a "
                   "stated density)" % (_fmt_mass(tot["mass"]),
                                        _fmt_vec(tot["cog"])))
    elif tot["count"]:
        out.append("- no centre of gravity: %d of %d solids have no density "
                   "assigned, so only volume is known"
                   % (tot["without_density"], tot["count"]))
    out.append("- parametric: %d spreadsheet aliases, %d expression bindings"
               % (len(aliases), len(bindings)))
    out.append("- not clean on arrival: %d objects" % len(bad))
    for n in notes[:8]:
        out.append("- %s" % n)
    out.append("The full inventory is in %s." % RESUME_NAME)
    return "\n".join(out)


def write_resume(log):
    """The file an agent reads first: what this project is, what state the
    logging was left in, and where the detail lives."""
    doc = App.getDocument(log.doc_name)
    chapters = sorted(glob.glob(os.path.join(log.writer.folder, "log_*.md")))
    names = sorted(o.Name for o in doc.Objects)
    out = [
        "# Resume: %s" % doc.Label,
        "",
        "- document: `%s`" % (doc.FileName or "(unsaved)"),
        "- FreeCAD: %s" % ".".join(App.Version()[0:3]),
        "- log state: %s" % read_state(doc),
        "- written by: AI Project Log %s" % __LOG_VERSION__,
        "- as of: %s" % now_iso(),
        "",
    ]

    # The geometry goes before the name list. An agent that reads only the
    # first screen should learn what this thing IS, not what the objects
    # happen to be called.
    try:
        out += [inventory_markdown(doc), ""]
    except BaseException as exc:
        out += ["## What is in this document", "",
                "The inventory could not be built: %s: %s"
                % (type(exc).__name__, exc), ""]

    out += [
        "## Tree (%d objects)" % len(names),
        "",
    ]
    for n in names:
        o = doc.getObject(n)
        out.append("- `%s` -- %s" % (n, getattr(o, "TypeId", "?")))
    out += ["", "## Chapters", ""]
    for c in chapters:
        out.append("- `%s` (%d bytes)"
                   % (os.path.basename(c), os.path.getsize(c)))

    # Report what is ACTUALLY embedded. 0.0.03 asserted a copy was inside the
    # .FCStd unconditionally; on the operator's own file LogCopy was empty,
    # so the resume file stated something untrue. A resume that lies is worse
    # than one that omits.
    copy = ""
    try:
        obj = log_object(doc)
        if obj is not None:
            copy = getattr(obj, COPY_PROP, "") or ""
    except BaseException:
        copy = ""
    out += [""]
    if copy:
        out += ["A copy of the log as at the last save also rides inside the "
                ".FCStd, on the %s object, property %s."
                % (LOG_OBJECT_NAME, COPY_PROP)]
    else:
        out += ["Nothing is embedded in the .FCStd yet: it carries a copy "
                "only once the document has been saved while logging. These "
                "files beside it are the whole record."]
    out += ["",
            "Read the chapters in order. The newest entries are at the end of",
            "the highest-numbered file. Entries marked (undo) or (redo) were",
            "caused by the operator undoing or redoing, not by a fresh",
            "decision."]
    path = os.path.join(log.writer.folder, RESUME_NAME)
    with open(path, "w", encoding="utf-8") as fh:
        fh.write("\n".join(out) + "\n")
    return path


# Every checkpoint refreshes the resume file. Done by wrapping Part 2's
# method rather than editing it, so Part 2 stays as written and tested.
_base_checkpoint = ProjectLog.checkpoint


def _checkpoint_and_resume(self, why):
    _base_checkpoint(self, why)
    try:
        write_resume(self)
    except BaseException:
        pass


ProjectLog.checkpoint = _checkpoint_and_resume


# The baseline entry. _RESUME.md is rewritten at every checkpoint, so it
# always describes the model as it is NOW; an agent reading the chapters in
# order needs to meet the model as it was BEFORE anything was done to it.
# Wrapped rather than edited into Part 2, for the same reason checkpoint is:
# Part 2 stays as written and as tested.
_base_install = ProjectLog.install


def _install_with_baseline(self):
    first = not self._installed
    _base_install(self)
    if not first:
        return
    try:
        doc = App.getDocument(self.doc_name)
        self.entry("baseline", inventory_summary(doc), fenced=False)
    except BaseException as exc:
        try:
            self.entry("baseline", "the opening inventory could not be "
                                   "measured: %s: %s"
                       % (type(exc).__name__, exc))
        except BaseException:
            pass


ProjectLog.install = _install_with_baseline


# ----------------------------------------------------------------------------
# An entry point for agents. The Rule 12 splash is a modal gate waiting for a
# human click, so a tool whose purpose is letting an AI resume a project could
# not be started by one. Over the Bridge an agent calls these through the
# published API: AIBridge.memory_start() / memory_stop() (see _AgentAPI
# below, v5.0.17) -- these module names themselves are not visible from the
# execute sandbox or a run_macro module.
# ----------------------------------------------------------------------------
NO_SPLASH_ATTR = "AI_PROJECT_LOG_NO_SPLASH"


def agent_start(doc=None):
    """Start logging without any GUI at all. Returns the log, or raises with
    a plain reason an agent can read."""
    doc = doc or App.ActiveDocument
    if doc is None:
        raise ValueError("no active document to log")
    if not getattr(doc, "FileName", ""):
        raise ValueError("save the document first; an unsaved document has "
                         "nowhere beside it to put a log")
    write_state(doc, "enabled")
    return start_for(doc)


def agent_stop(doc=None):
    doc = doc or App.ActiveDocument
    if doc is None:
        return 0
    log = LOGS.get(doc.Name)
    if log is None:
        return 0
    size = 0
    try:
        size = embed_log(log)
    except BaseException:
        pass
    write_state(doc, "off")
    log.stop()
    LOGS.pop(doc.Name, None)
    return size


# ===========================================================================
# AGENT API -- the Bridge's memory and multicore verbs, published where an
# agent can actually reach them.
# ---------------------------------------------------------------------------
# Everything above (the project log, the document inventory, the capture
# worker, the outsource registry) was unreachable from the command channel
# until 5.0.17: the execute sandbox builds a fresh restricted namespace and
# run_macro loads the file as a fresh module, so none of this macro's names
# were visible to the agent the Bridge exists to serve. Verified live on
# 5.0.16 -- every probe for agent_start, start_capture and the rest came
# back NameError, while the GUI used them happily.
#
# The API is one object on the App module -- the single namespace every
# route already shares: the execute sandbox pre-loads App (and gets the
# object directly as AIBridge), and any run_macro file imports FreeCAD.
# Named verbs with typed parameters only; nothing here takes a code string.
# Errors raise with a plain reason, which the Bridge's own error_report
# path carries back to the agent verbatim.
# ===========================================================================
class _AgentAPI(object):
    """App.AIBridge -- parametric memory and multicore verbs for agents.

    Memory verbs give a document a memory that travels WITH it (a log
    folder beside the .FCStd and an embedded copy inside it); multicore
    verbs do heavy work in a second process so this session never blocks.
    Call help() for the one-screen list.
    """

    # -- parametric memory ---------------------------------------------------
    def memory_start(self, doc=None):
        """Begin logging DOC (default: the active document). The document
        must be saved once. Returns the log folder path."""
        log = agent_start(doc)
        return log.writer.folder

    def memory_stop(self, doc=None):
        """Checkpoint, embed the log inside the .FCStd and stop logging.
        Returns the embedded size in bytes (0 if nothing was running)."""
        return agent_stop(doc)

    def memory_state(self, doc=None):
        """'enabled', 'paused' or 'off' for DOC (default: active)."""
        doc = doc or App.ActiveDocument
        if doc is None:
            return "off"
        return read_state(doc)

    def memory_note(self, text, doc=None, kind="agent"):
        """Record one agent decision or observation in DOC's running log."""
        doc = doc or App.ActiveDocument
        if doc is None:
            raise ValueError("no active document")
        log = LOGS.get(doc.Name)
        if log is None:
            raise ValueError("logging is not running on '%s'; call "
                             "memory_start() first" % doc.Name)
        log.entry(kind, str(text), fenced=False)
        return "noted in %s" % os.path.basename(log.writer.folder)

    def memory_checkpoint(self, doc=None, why="agent checkpoint"):
        """Flush to disk, rewrite _RESUME.md and re-embed into the .FCStd
        without stopping. Returns the embedded size in bytes."""
        doc = doc or App.ActiveDocument
        if doc is None:
            raise ValueError("no active document")
        log = LOGS.get(doc.Name)
        if log is None:
            raise ValueError("logging is not running on '%s'" % doc.Name)
        log.checkpoint(why)
        return embed_log(log)

    def memory_recall(self, doc=None):
        """The memory DOC carries: the copy embedded inside the .FCStd when
        there is one (it travels with the file), else the log beside the
        file. Returns '' for a document with no memory at all."""
        doc = doc or App.ActiveDocument
        if doc is None:
            raise ValueError("no active document")
        obj = log_object(doc)
        if obj is not None:
            path = getattr(obj, COPY_PROP, "") or ""
            if path and os.path.isfile(path):
                with open(path, encoding="utf-8") as fh:
                    return fh.read()
        try:
            folder = log_dir_path(doc)
        except ValueError:
            return ""          # never saved -> nowhere a log could be
        if not os.path.isdir(folder):
            return ""
        pieces = []
        resume = os.path.join(folder, RESUME_NAME)
        if os.path.isfile(resume):
            with open(resume, encoding="utf-8") as fh:
                pieces.append(fh.read())
        for c in sorted(glob.glob(os.path.join(folder, "log_*.md"))):
            with open(c, encoding="utf-8") as fh:
                pieces.append(fh.read())
        return "\n\n".join(pieces)

    def inventory(self, doc=None, full=False):
        """Measure DOC before touching it: extent, mass where a density is
        stated, parametric knobs, health. full=True for the whole report."""
        doc = doc or App.ActiveDocument
        if doc is None:
            raise ValueError("no active document")
        return inventory_markdown(doc) if full else inventory_summary(doc)

    # -- multicore -----------------------------------------------------------
    def capture(self, doc=None, out_dir="", preset="Medium", **kw):
        """Photograph DOC -- whole view plus section slices -- in a SECOND
        FreeCAD process, so this session never blocks. The document must be
        saved. Returns the job folder; poll capture_status() on it. Extra
        keywords pass through to start_capture (slices, axes, objects,
        second_degree, fidelity, width, height)."""
        doc = doc or App.ActiveDocument
        if doc is None:
            raise ValueError("no active document")
        if not out_dir:
            out_dir = os.path.join(AI_IO_DIR, "capture", "%s_%s" % (
                doc.Name, time.strftime("%Y%m%d_%H%M%S")))
        ok, msg, job = start_capture(doc, out_dir, preset=preset, **kw)
        if not ok:
            raise RuntimeError(msg)
        return job

    def capture_status(self, job_dir):
        """The worker's manifest once it finishes (status, images, section
        profiles), else {'status': 'running'}. Never blocks."""
        man = os.path.join(job_dir, "capture_manifest.json")
        if not os.path.isfile(man):
            return {"status": "running", "job_dir": job_dir}
        with open(man, encoding="utf-8-sig") as fh:
            return json.load(fh)

    # -- outsource (mesh tools in their own process) ---------------------------
    def outsource(self, key=None):
        """State of every outsource target, or of one by key."""
        if key:
            t = outsource_target(key)
            if t is None:
                raise ValueError("no outsource target '%s'" % key)
            return outsource_state(t)
        return [outsource_state(t) for t in OUTSOURCE_TARGETS]

    def push(self, key, doc=None, objects=None):
        """Export DOC's solids into the target's push folder. Returns the
        exported file path."""
        t = outsource_target(key)
        if t is None:
            raise ValueError("no outsource target '%s'" % key)
        ok, msg, path = outsource_push(t, doc or App.ActiveDocument, objects)
        if not ok:
            raise RuntimeError(msg)
        return path

    def pull(self, key, doc=None):
        """Import every NEW file from the target's pull folder into DOC.
        Returns the list of imported names (may be empty)."""
        t = outsource_target(key)
        if t is None:
            raise ValueError("no outsource target '%s'" % key)
        ok, msg, names = outsource_pull(t, doc or App.ActiveDocument)
        if not ok and not names:
            raise RuntimeError(msg)
        return names

    def launch(self, key):
        """Start (or find) the target's own server/app. Returns its URL or
        the launcher's message when there is no URL."""
        t = outsource_target(key)
        if t is None:
            raise ValueError("no outsource target '%s'" % key)
        ok, msg, url = outsource_launch(t)
        if not ok:
            raise RuntimeError(msg)
        return url or msg

    def help(self):
        """One screen: every verb and what it does."""
        return (
            "App.AIBridge -- agent verbs (also pre-loaded as AIBridge in "
            "execute commands)\n"
            "\n"
            "PARAMETRIC MEMORY (travels with the document):\n"
            "  memory_recall(doc=None)      what this document already knows\n"
            "  memory_start(doc=None)       begin logging (doc must be saved)\n"
            "  memory_note(text)            record a decision in the log\n"
            "  memory_checkpoint()          flush + re-embed into the .FCStd\n"
            "  memory_stop()                embed and stop\n"
            "  memory_state()               'enabled', 'paused' or 'off'\n"
            "  inventory(full=False)        measured summary of the model\n"
            "\n"
            "MULTICORE (a second process does the work; this GUI never "
            "blocks):\n"
            "  job = capture(preset='Medium', slices=12, axes=['x','y','z'])\n"
            "  capture_status(job)          manifest when the worker is done\n"
            "\n"
            "OUTSOURCE (mesh tools in their own process):\n"
            "  outsource()                  every target and its state\n"
            "  push(key)  pull(key)  launch(key)\n")


def _publish_agent_api():
    """Put the API where every execution route can see it. Never raises:
    a Bridge that cannot publish its API must still start."""
    try:
        api = _AgentAPI()
        setattr(App, "AIBridge", api)
        return api
    except BaseException:
        return None


AGENT_API = _publish_agent_api()


# ----------------------------------------------------------------------------
# GUI 2. Non-modal per Rule 14, pinned to the main window so Python's GC does
# not destroy it when the macro script exits, version in the title per Rule 63.
# ----------------------------------------------------------------------------
class AIProjectLogPanel:

    PIN = "_ai_project_log_instance"

    def __init__(self, host=None, show_donation=True):
        # Bridge 3.5.0: when the Bridge hosts this panel as a tab, the
        # widgets go into the page it hands over rather than a window of
        # their own, and the Support & Donation block is left to the dialog
        # that owns the tabs so it is not drawn twice. Standalone behaviour
        # is unchanged: no argument, same window as before.
        self.hosted = host is not None
        if self.hosted:
            self.dialog = host
        else:
            self.dialog = QtWidgets.QDialog(Gui.getMainWindow())
            self.dialog.setWindowTitle("AI Project Log " + __LOG_VERSION__)
            self.dialog.setMinimumWidth(460)

        lay = QtWidgets.QVBoxLayout(self.dialog)

        self.doc_label = QtWidgets.QLabel()
        self.doc_label.setWordWrap(True)
        lay.addWidget(self.doc_label)

        self.state_label = QtWidgets.QLabel()
        self.state_label.setStyleSheet("font-weight: bold; color: #00bcd4;")
        lay.addWidget(self.state_label)

        self.folder_label = QtWidgets.QLabel()
        self.folder_label.setWordWrap(True)
        # The same values the Bridge's own path style uses, written
        # out longhand ON PURPOSE. This line is inside the region
        # spliced in whole from AI_Project_Log, which is kept
        # self-contained so the two copies stay reconcilable: its
        # only outside names are the Qt bindings and DonationPanel.
        # Calling the shared helper here made it a third name, and
        # check_350_static caught it. Keep the two in step by hand.
        self.folder_label.setStyleSheet(
            "color: #aab3c2; font-size: 9pt;")
        lay.addWidget(self.folder_label)

        # v0.0.13: one running control, not three. Start and Pause are
        # the same button in two states, so they are one button; Embed is
        # gone because saving embeds anyway; Refresh is gone because the
        # 800 ms poll already does it and a Refresh button tells the
        # operator the display might be stale.
        row = QtWidgets.QHBoxLayout()
        self.btn_run = QtWidgets.QPushButton("Start logging")
        self.btn_run.setToolTip(
            "Start, pause and resume. A copy of the log rides inside the "
            ".FCStd automatically every time you save -- there is nothing "
            "to press for that.")
        self.btn_stop = QtWidgets.QPushButton("Stop and embed")
        self.btn_stop.setToolTip(
            "Finish: write the copy into the document and stop. Pause "
            "keeps the log and picks up where it left off; this does not.")
        self.btn_open = QtWidgets.QPushButton("Open log folder")
        for b in (self.btn_run, self.btn_stop, self.btn_open):
            row.addWidget(b)
        row.addStretch()
        lay.addLayout(row)

        # The way out of "this document has never been saved, so there is
        # nowhere to write the log". Not everyday controls, so they are
        # only on screen when that is actually the problem.
        self.row_unsaved = QtWidgets.QWidget()
        row3 = QtWidgets.QHBoxLayout(self.row_unsaved)
        row3.setContentsMargins(0, 0, 0, 0)
        self.btn_new = QtWidgets.QPushButton("New document...")
        self.btn_saveas = QtWidgets.QPushButton("Save document as...")
        row3.addWidget(self.btn_new)
        row3.addWidget(self.btn_saveas)
        row3.addStretch()
        lay.addWidget(self.row_unsaved)

        self.btn_run.clicked.connect(self._on_run)
        self.btn_stop.clicked.connect(self._on_stop)
        self.btn_open.clicked.connect(self._on_open)
        self.btn_new.clicked.connect(self._on_new)
        self.btn_saveas.clicked.connect(self._on_saveas)

        sep = QtWidgets.QFrame()
        sep.setFrameShape(QtWidgets.QFrame.Shape.HLine)
        sep.setStyleSheet(
            "color: #00bcd4; background: #00bcd4; max-height: 1px;")
        lay.addWidget(sep)

        if show_donation:
            self.donation_panel = DonationPanel()
            lay.addWidget(self.donation_panel)
        else:
            self.donation_panel = None

        # The panel used to read state once, at construction, so saving the
        # document outside it left Start greyed out with no way to recover.
        self._sig = None
        self._said_error = None
        self._poll = QtCore.QTimer()
        self._poll.setInterval(800)
        self._poll.timeout.connect(self._maybe_refresh)
        self._poll.start()

        self._refresh()

    # -- helpers ------------------------------------------------------------
    def _doc(self):
        return App.ActiveDocument

    def _log(self):
        doc = self._doc()
        return LOGS.get(doc.Name) if doc is not None else None

    def _signature(self):
        doc = self._doc()
        if doc is None:
            return (None,)
        # Widened in 0.0.13 when the manual Refresh button was removed:
        # the poll is now the only thing keeping this panel honest, so it
        # must notice the folder appearing and the document being
        # renamed, both of which it previously missed.
        try:
            folder = log_dir_path(doc) if doc.FileName else ""
            there = os.path.isdir(folder) if folder else False
        except BaseException:
            there = False
        return (doc.Name, doc.Label, doc.FileName, read_state(doc),
                self._log() is not None, there)

    def _maybe_refresh(self):
        # The writer thread cannot report its own failures -- touching
        # App.Console from there would re-enter the broker's hook and loop. It
        # parks the message on last_error; this is the main thread reading it,
        # and the latch makes "report once" true in the code, not just in the
        # comment.
        log = self._log()
        if log is not None:
            err = getattr(log.writer, "last_error", None)
            if err and err != self._said_error:
                self._said_error = err
                self._say("WRITE FAILED: %s -- entries are being queued but "
                          "not saved." % err)
            elif not err:
                self._said_error = None
        # 0.0.05: the hooks are now total, which means a failure inside one
        # is invisible by construction. Counting is not reporting (Rule 55),
        # so the count is surfaced here.
        try:
            BROKER.verify()
        except BaseException:
            pass
        rea = getattr(BROKER, "reattached", 0)
        if rea and rea != getattr(self, "_said_reattach", 0):
            self._said_reattach = rea
            self._say("STREAM RE-ATTACHED x%d: %s"
                      % (rea, BROKER.last_reattach))
        hooks = getattr(BROKER, "hook_errors", 0)
        if hooks and hooks != getattr(self, "_said_hooks", 0):
            self._said_hooks = hooks
            self._say("CAPTURE FAULT x%d: %s -- some console output may be "
                      "missing from this log."
                      % (hooks, BROKER.last_hook_error))
        try:
            sig = self._signature()
        except BaseException:
            return
        if sig != self._sig:
            self._sig = sig
            self._refresh()

    def _refresh(self):
        doc = self._doc()
        self.btn_new.setEnabled(True)
        if doc is None:
            self.doc_label.setText(
                "No document open. Press New document... to make one, "
                "or open an existing .FCStd.")
            self.state_label.setText("state: no document")
            self.folder_label.setText("")
            self.btn_run.setText("Start logging")
            for b in (self.btn_run, self.btn_stop, self.btn_open,
                      self.btn_saveas):
                b.setEnabled(False)
            self.row_unsaved.setVisible(True)
            self._sig = (None,)
            return
        saved = bool(doc.FileName)
        self.doc_label.setText("Document: %s" % doc.Label)
        state = read_state(doc)
        live = self._log() is not None
        self.state_label.setText("state: %s%s"
                                 % (state, "" if live else "  (not running)"))
        if saved:
            self.folder_label.setText(log_dir_path(doc))
        else:
            self.folder_label.setText(
                "This document has never been saved, so there is nowhere "
                "beside it to write the log. Press Save document as... and "
                "Start will come alive.")
        # One button, three faces. Resume rather than Start when there
        # is a paused log to pick up, so the operator can see that their
        # history is still there.
        self.btn_run.setText("Pause" if live
                             else ("Resume" if state == "paused"
                                   else "Start logging"))
        self.btn_run.setEnabled(saved)
        self.btn_stop.setEnabled(live or state == "paused")
        self.btn_open.setEnabled(saved and os.path.isdir(log_dir_path(doc)))
        self.btn_saveas.setEnabled(not live)
        # New / Save as are the escape hatch from an unsaved document, so
        # they are only on screen when that is the problem.
        self.row_unsaved.setVisible(not saved)
        self._sig = self._signature()

    def _say(self, msg):
        App.Console.PrintMessage("[AI_ProjectLog] %s\n" % msg)

    # -- getting out of the unsaved-document dead end -----------------------
    def _on_new(self):
        doc = App.newDocument("Unnamed")
        try:
            Gui.ActiveDocument = Gui.getDocument(doc.Name)
        except BaseException:
            pass
        self._say("created a new document; save it to give the log a home.")
        self._refresh()
        self._on_saveas()

    def _on_saveas(self):
        doc = self._doc()
        if doc is None:
            self._refresh()
            return
        start = doc.FileName or os.path.join(
            App.getUserAppDataDir(), (doc.Label or "Unnamed") + ".FCStd")
        path, _ = QtWidgets.QFileDialog.getSaveFileName(
            self.dialog, "Save document as", start,
            "FreeCAD document (*.FCStd)")
        if not path:
            self._say("save cancelled; nothing changed.")
            self._refresh()
            return
        if not path.lower().endswith(".fcstd"):
            path += ".FCStd"
        try:
            doc.saveAs(path)
        except BaseException as exc:
            self._say("could not save: %s" % exc)
            self._refresh()
            return
        self._say("saved to %s" % path)
        self._refresh()

    # -- actions ------------------------------------------------------------
    def _on_run(self):
        """Start, pause or resume -- whichever this button currently is.

        The operator should not have to work out which of three buttons
        applies to the state they are already looking at.
        """
        if self._log() is not None:
            return self._on_pause()
        return self._on_start()

    def _on_start(self):
        doc = self._doc()
        if doc is None:
            self._say("no document open; press New document... first.")
            self._refresh()
            return
        if not doc.FileName:
            self._on_saveas()
            doc = self._doc()
            if doc is None or not doc.FileName:
                return
        write_state(doc, "enabled")
        start_for(doc)
        self._say("logging to %s -- a copy goes inside the .FCStd "
                  "every time you save." % log_dir_path(doc))
        self._refresh()

    def _on_pause(self):
        doc, log = self._doc(), self._log()
        if doc is None or log is None:
            self._refresh()
            return
        write_state(doc, "paused")
        log.entry("note", "logging paused by the operator")
        log.stop(reason="logging paused")
        LOGS.pop(doc.Name, None)
        self._say("paused; the log is intact and will resume on Start.")
        self._refresh()

    def _on_stop(self):
        doc, log = self._doc(), self._log()
        if doc is None or log is None:
            self._refresh()
            return
        size = 0
        try:
            size = embed_log(log)
        except BaseException:
            pass
        write_state(doc, "off")
        log.stop()
        LOGS.pop(doc.Name, None)
        self._say("stopped; %d bytes embedded. Save to keep it." % size)
        self._refresh()


    def _on_open(self):
        doc = self._doc()
        if doc is None or not doc.FileName:
            return
        folder = log_dir_path(doc)
        try:
            QtGui.QDesktopServices.openUrl(QtCore.QUrl.fromLocalFile(folder))
        except BaseException:
            self._say(folder)

    # -- lifecycle ----------------------------------------------------------
    def show(self):
        self.dialog.finished.connect(self._cleanup)
        self.dialog.show()          # Rule 14: never exec() for a main GUI

    def _cleanup(self):
        # Rule 17: stop the timer, or it keeps firing at a dead widget.
        if not _SHUTTING_DOWN:
            try:
                self._poll.stop()
                self._poll.timeout.disconnect()
            except (RuntimeError, TypeError):
                pass
        try:
            mw = Gui.getMainWindow()
            if getattr(mw, AIProjectLogPanel.PIN, None) is self:
                delattr(mw, AIProjectLogPanel.PIN)
        except (AttributeError, RuntimeError, TypeError):
            pass


# ===========================================================================
# end of the spliced AI Project Log
# ===========================================================================


class GradientLogoLabel(QtWidgets.QWidget):
    """Standard Imagineering gradient logo (green -> cyan -> blue),
    painted via QPainter — reference impl from 150_Ladder_Safety."""

    def __init__(self, text="Imαgineering", size=26, parent=None):
        super(GradientLogoLabel, self).__init__(parent)
        self._text = text
        self._font = QtGui.QFont("Arial", size, QtGui.QFont.Bold)
        fm = QtGui.QFontMetrics(self._font)
        tr = fm.boundingRect(self._text)
        self.setFixedSize(tr.width() + 20, tr.height() + 20)

    def paintEvent(self, event):
        painter = QtGui.QPainter(self)
        painter.setRenderHint(QtGui.QPainter.Antialiasing)
        painter.setFont(self._font)
        gradient = QtGui.QLinearGradient(0, 0, self.width(), 0)
        gradient.setColorAt(0.0, QtGui.QColor(ACCENT_GREEN))
        gradient.setColorAt(0.5, QtGui.QColor(ACCENT_CYAN))
        gradient.setColorAt(1.0, QtGui.QColor(ACCENT_BLUE))
        painter.setPen(QtGui.QPen(QtGui.QBrush(gradient), 1))
        painter.drawText(self.rect(), Qt.AlignCenter, self._text)
        painter.end()


# ============================================================
# OLLAMA - LOCAL AI AGENT [v3.4.0 PHASES 2-10]
# ============================================================
# ARCHITECTURAL CONTRACT - read before touching anything below:
#
#   1. Ollama is a CLIENT of the bridge, never a bypass of it. Nothing in
#      this section calls exec(). Generated code is appended to
#      AI_INPUT_FILE as JSONL and picked up by the existing
#      process_ai_commands() poll, so it passes the same AST sandbox, dedup,
#      watchdog and learning path as every other agent.
#
#   2. This client code must NEVER be routed through
#      SecureCommandExecutor.validate_command(). Config.FORBIDDEN_PATTERNS
#      blocks 'import os', 'open(' and friends - the sandbox exists to guard
#      MODEL OUTPUT, not the client that fetches it.
#
#   3. THE THREAD BOUNDARY IS ABSOLUTE. OllamaWorker runs network I/O and
#      nothing else. No App, no Gui, no document access, no App.Console from
#      inside run(). FreeCAD's API is not thread-safe. Everything crosses
#      back via Qt signals, which Qt queues onto the GUI thread for us.
#
#   4. Context building touches the live document, so it happens on the GUI
#      thread BEFORE the worker starts, never inside it.
# ============================================================

import hashlib as _hashlib
import uuid as _uuid

# Set on the GUI thread around a generation so the v3.3.3 watchdog can tell
# "the local model is thinking" (fine, off-thread) from "a command is holding the GUI
# thread" (a real freeze). Never set from inside the worker.
_ollama_generating = False
_ollama_dialog = None

OLLAMA_CORE_RULES = """You are a FreeCAD Python assistant running locally via Ollama.

CRITICAL EXECUTION RULES:
- Each command runs in a FRESH exec() scope. Variables DO NOT persist between commands.
- EVERY command must start with: doc = App.ActiveDocument
- Re-declare every import the command needs (import Part, import math, ...).
- Use real newlines, never semicolons, for for/if blocks.
- End with doc.recompute() when geometry changed.
- ALLOWED: App, Gui, FreeCAD, FreeCADGui, Part, Draft, Sketcher, Mesh, math,
  datetime, PartDesign, Arch, TechDraw, Path, Spreadsheet.
- BLOCKED: os, sys, subprocess, open(), eval(), exec().
- Prefer ONE larger command over many small ones.

BACKUPS -- YOUR JOB TO RAISE, NOT THE OPERATOR'S TO REMEMBER:
- LIVE DOCUMENT STATE below carries a "Backup" line. When it says a fork
  is DUE, say so in your reply, in one sentence, before the geometry.
- Ask for a fork before anything hard to undo: a boolean on a shape that
  took work, a bulk property rewrite, a delete, or a recompute of a
  document that is already in a bad state.
- Say it once per milestone, not every command. A reminder that fires
  constantly is one the operator learns to scroll past.

Reply with a single ```python fenced block containing the complete command,
plus one short sentence of explanation. No preamble, no alternatives."""


def _estimate_tokens(text):
    """Rough token count. chars/3.5 tracks Qwen tokenisers closely enough
    for budgeting; we only need to know when we're near the ceiling."""
    return int(len(text) / 3.5) if text else 0


# ============================================================
# PHASE 4 - CONTEXT BUILDER
# ============================================================

class OllamaContextBuilder:
    """Assembles the system prompt from the bridge's own knowledge.

    This is where the knowledge base earns its keep: a small local model with
    five retrieved, verified patterns beats a bigger model with none. Runs on
    the GUI thread only - it reads the live document.
    """

    def __init__(self):
        self.last_built = None
        self.last_hash = None
        self.last_tokens = 0
        self.last_report = None   # v3.4.3: diagnostics for the Context inspector

    # ---- components ----

    @staticmethod
    def core_rules():
        return OLLAMA_CORE_RULES

    @staticmethod
    def live_document_state():
        """Current document snapshot. GUI THREAD ONLY."""
        try:
            doc = App.ActiveDocument
            if doc is None:
                return ("LIVE DOCUMENT STATE:\n"
                        "  No active document. Your FIRST command must create one:\n"
                        "  doc = App.newDocument('Unnamed')\n")

            lines = ["LIVE DOCUMENT STATE:",
                     "  Document: %s" % doc.Name,
                     "  Objects: %d" % len(doc.Objects)]
            # v4.0.15: so the AGENT can do the reminding. A backup prompt
            # that lives only in the GUI is invisible to the thing doing
            # the work.
            try:
                _fs = fork_state(doc)
                lines.append(
                    "  Backup: %s -- %s"
                    % ("FORK DUE" if _fs.get("due") else "ok",
                       _fs.get("why", "")))
            except BaseException:
                pass
            for obj in doc.Objects[:25]:
                try:
                    lines.append("    - %s (%s)" % (obj.Name, obj.TypeId))
                except Exception:
                    continue
            if len(doc.Objects) > 25:
                lines.append("    ... and %d more" % (len(doc.Objects) - 25))

            try:
                sel = Gui.Selection.getSelection()
                if sel:
                    lines.append("  Selected: %s"
                                 % ", ".join(o.Name for o in sel[:10]))
            except Exception:
                pass
            return "\n".join(lines) + "\n"
        except Exception as e:
            return "LIVE DOCUMENT STATE: unavailable (%s)\n" % e

    # ---- retrieval (v3.4.3) ----

    # Words carrying no retrieval signal. 'make'/'create' are excluded
    # deliberately: they match makeBox, makeSphere, makeCylinder and every
    # other constructor, so they return everything and rank nothing.
    _STOPWORDS = {
        'the', 'and', 'for', 'with', 'without', 'from', 'into', 'onto',
        'are', 'was', 'were', 'been', 'being', 'have', 'has', 'had', 'does',
        'did', 'will', 'would', 'should', 'can', 'could', 'may', 'might',
        'must', 'shall', 'this', 'that', 'these', 'those', 'its', 'then',
        'than', 'please', 'you', 'your', 'need', 'want', 'make', 'create',
        'add', 'new', 'some', 'any', 'all', 'each', 'about', 'using', 'use',
        'like', 'when', 'how', 'what', 'which', 'give', 'get', 'put', 'set',
    }

    # Natural language -> FreeCAD API vocabulary. Users ask for "a hole";
    # the knowledge base indexes "cut" and "boolean". Without this bridge the
    # right pattern is present in the KB and never found.
    _DOMAIN_ALIASES = {
        'box': ['box', 'makebox'], 'cube': ['box', 'makebox'],
        'cylinder': ['cylinder', 'makecylinder'], 'tube': ['cylinder'],
        'sphere': ['sphere', 'makesphere'], 'ball': ['sphere'],
        'cone': ['cone', 'makecone'], 'torus': ['torus'],
        'hole': ['cut', 'boolean', 'cylinder'], 'bore': ['cut', 'cylinder'],
        'cut': ['cut', 'boolean'], 'subtract': ['cut', 'boolean'],
        'union': ['fuse', 'boolean'], 'join': ['fuse', 'boolean'],
        'merge': ['fuse', 'boolean'], 'combine': ['fuse', 'boolean'],
        'intersect': ['common', 'boolean'], 'boolean': ['boolean'],
        'sketch': ['sketcher', 'sketch'], 'constraint': ['sketcher', 'constraint'],
        'constrain': ['sketcher', 'constraint'],
        'extrude': ['extrude', 'pad'], 'pad': ['pad', 'partdesign'],
        'pocket': ['pocket', 'partdesign'], 'revolve': ['revolution', 'partdesign'],
        'loft': ['loft'], 'sweep': ['sweep'],
        'fillet': ['fillet'], 'round': ['fillet'], 'chamfer': ['chamfer'],
        'plate': ['plate', 'quad', 'shell'], 'slab': ['plate', 'quad'],
        'shell': ['shell'], 'beam': ['member', 'beam'], 'truss': ['member'],
        'column': ['member'], 'frame': ['member'],
        'wire': ['wire', 'polygon'], 'polygon': ['polygon', 'wire'],
        'line': ['line', 'draft'], 'circle': ['circle', 'draft'],
        'arc': ['arc'], 'spline': ['bspline', 'spline'],
        'array': ['array', 'draft'], 'pattern': ['array'],
        'mirror': ['mirror'], 'clone': ['clone', 'draft'],
        'move': ['placement', 'vector'], 'position': ['placement', 'vector'],
        'rotate': ['rotation', 'placement'], 'rotation': ['rotation', 'placement'],
        'translate': ['placement', 'vector'], 'placement': ['placement'],
        'colour': ['viewobject', 'shapecolor'], 'color': ['viewobject', 'shapecolor'],
        'transparent': ['transparency', 'viewobject'],
        'hide': ['visibility', 'viewobject'], 'show': ['visibility', 'viewobject'],
        'mesh': ['mesh'], 'stl': ['mesh', 'export'],
        'export': ['export'], 'import': ['import'],
        'spreadsheet': ['spreadsheet'], 'cell': ['spreadsheet'],
        'techdraw': ['techdraw'], 'drawing': ['techdraw'],
        'document': ['document', 'newdocument'], 'recompute': ['recompute'],
        'select': ['selection'], 'selection': ['selection'], 'selected': ['selection'],
        'material': ['material'], 'section': ['section'],
        'measure': ['measure'], 'volume': ['volume'], 'area': ['area'],
    }

    @classmethod
    def extract_query_terms(cls, prompt, limit=12):
        """Turn a natural-language prompt into searchable index terms.

        THE BUG THIS FIXES: search_knowledge() tests
        `query_lower in category.lower()` - it substring-matches the WHOLE
        query against category names. 'box' matched; 'create a 10mm box with
        a hole' matched nothing at all. Passing raw prompts meant retrieval
        silently returned ZERO hits for every realistic request, which is why
        the injected context never grew beyond the core rules.
        """
        if not prompt:
            return []
        words = re.findall(r"[a-zA-Z_]{2,}", prompt.lower())
        terms = []
        for word in words:
            if word in cls._STOPWORDS or len(word) < 3:
                continue
            if word not in terms:
                terms.append(word)
            for alias in cls._DOMAIN_ALIASES.get(word, []):
                if alias not in terms:
                    terms.append(alias)
        return terms[:limit]

    @staticmethod
    def _format_hit(hit):
        """Compact one-line rendering.

        The previous implementation json.dumps()'d each hit with indent=1,
        burning 3-5x the tokens for identical information - expensive when the
        entire budget is 6000.
        """
        try:
            if not isinstance(hit, dict):
                return str(hit)[:300]
            if 'key' in hit and 'category' in hit:
                return "%s.%s: %s" % (hit['category'], hit['key'],
                                      str(hit.get('data', ''))[:240])
            if 'category' in hit and isinstance(hit.get('data'), dict):
                keys = ", ".join(list(hit['data'].keys())[:12])
                return "%s: %s" % (hit['category'], keys)
            if 'name' in hit:
                desc = str(hit.get('description', ''))[:160]
                cmds = hit.get('key_commands') or []
                extra = ((" | commands: " + ", ".join(str(c)[:40] for c in cmds[:3]))
                         if cmds else "")
                return "workbench %s: %s%s" % (hit['name'], desc, extra)
            return json.dumps(hit)[:300]
        except Exception:
            return str(hit)[:300]

    @staticmethod
    def _score(text, terms):
        """Rank by distinct term coverage; whole-word matches count double."""
        if not text or not terms:
            return 0
        low = text.lower()
        score = 0
        for term in terms:
            try:
                if re.search(r"\b%s\b" % re.escape(term), low):
                    score += 2
                elif term in low:
                    score += 1
            except Exception:
                continue
        return score

    @classmethod
    def retrieve_patterns(cls, prompt, budget_tokens=2000):
        """Search PER TERM, merge, rank by relevance, fill to budget.

        Returns (text, report). The report feeds the Context inspector so a
        thin context is diagnosable instead of mysterious.
        """
        global _tech_reviewer
        report = {'terms': [], 'raw_hits': 0, 'ranked_hits': 0, 'used_tokens': 0, 'note': ''}
        if not _tech_reviewer or not getattr(_tech_reviewer, 'loaded', False):
            report['note'] = 'knowledge base not loaded'
            return "", report

        terms = cls.extract_query_terms(prompt)
        report['terms'] = terms
        if not terms:
            report['note'] = 'no searchable terms in prompt'
            return "", report

        seen = {}
        for term in terms:
            for search in ('search_knowledge', 'search_workbenches'):
                fn = getattr(_tech_reviewer, search, None)
                if not fn:
                    continue
                try:
                    hits = fn(term) or []
                except Exception:
                    continue
                for hit in hits:
                    text = cls._format_hit(hit)
                    if text and text not in seen:
                        seen[text] = cls._score(text, terms)

        report['raw_hits'] = len(seen)
        if not seen:
            report['note'] = 'no knowledge-base matches for these terms'
            return "", report

        ranked = sorted(seen.items(), key=lambda kv: (-kv[1], len(kv[0])))
        chosen, used = [], 0
        for text, score in ranked:
            cost = _estimate_tokens(text)
            if used + cost > budget_tokens:
                break
            chosen.append(text)
            used += cost

        report['ranked_hits'] = len(chosen)
        report['used_tokens'] = used
        if not chosen:
            report['note'] = 'hits found but all exceeded the token budget'
            return "", report
        return ("RELEVANT KNOWLEDGE BASE PATTERNS (verified APIs, ranked by relevance):\n"
                + "\n".join("- " + c for c in chosen) + "\n"), report

    @classmethod
    def recent_successes(cls, prompt="", limit=5, budget_tokens=1200):
        """VERIFIED successful commands, ranked by relevance to the prompt.

        Previously pure recency: the last five verified commands regardless of
        whether they had anything to do with the request. Relevance now wins,
        with recency as fallback when nothing scores - so an unrelated or first
        prompt still gets useful examples rather than none.

        PROVENANCE GATE (Phase 7): unverified patterns - including the local
        model's own earlier output - stay excluded.
        """
        global _learning_system
        report = {'candidates': 0, 'scored': 0, 'fallback_recency': False, 'used_tokens': 0}
        if not _learning_system:
            return "", report
        try:
            patterns = _learning_system.db.get('successful_patterns', [])
        except Exception:
            return "", report

        verified = [p for p in patterns if p.get('verified', True)]
        report['candidates'] = len(verified)
        if not verified:
            return "", report

        terms = cls.extract_query_terms(prompt)
        scored = []
        for pattern in verified:
            cmd = str(pattern.get('command', ''))
            if not cmd:
                continue
            scored.append((cls._score(cmd, terms) if terms else 0, cmd))

        relevant = [(s, c) for s, c in scored if s > 0]
        if relevant:
            relevant.sort(key=lambda sc: -sc[0])
            ordered = [c for _, c in relevant]
            report['scored'] = len(relevant)
        else:
            ordered = [c for _, c in scored][::-1]   # most recent first
            report['fallback_recency'] = True

        chosen, used = [], 0
        for cmd in ordered:
            snippet = cmd[:600]
            cost = _estimate_tokens(snippet)
            if used + cost > budget_tokens or len(chosen) >= limit:
                break
            chosen.append(snippet)
            used += cost

        report['used_tokens'] = used
        if not chosen:
            return "", report
        header = ("PROVEN COMMANDS FROM THIS BRIDGE (verified, most recent):\n"
                  if report['fallback_recency'] else
                  "PROVEN COMMANDS FROM THIS BRIDGE (verified, ranked by relevance):\n")
        return header + "\n---\n".join(chosen) + "\n", report


    # ---- assembly ----

    def build(self, user_prompt="", include_document=True):
        """Return the full system prompt, capped at the configured budget.

        Records self.last_report so the Context inspector can explain WHY the
        injected context is the size it is - which term set was searched, how
        many hits came back, and whether pattern selection fell back to
        recency. A thin context should be diagnosable, not mysterious.
        """
        budget = Config.OLLAMA_CONTEXT_BUDGET_TOKENS
        parts = [self.core_rules()]
        used = _estimate_tokens(parts[0])
        report = {'core_tokens': used, 'doc_tokens': 0}

        if include_document:
            doc_state = self.live_document_state()
            if used + _estimate_tokens(doc_state) < budget:
                parts.append(doc_state)
                used += _estimate_tokens(doc_state)
                report['doc_tokens'] = _estimate_tokens(doc_state)

        remaining = max(0, budget - used)
        patterns, kb_report = self.retrieve_patterns(user_prompt, int(remaining * 0.6))
        report['knowledge'] = kb_report
        if patterns:
            parts.append(patterns)
            used += _estimate_tokens(patterns)

        remaining = max(0, budget - used)
        successes, pat_report = self.recent_successes(
            prompt=user_prompt, budget_tokens=int(remaining * 0.8))
        report['patterns'] = pat_report
        if successes:
            parts.append(successes)
            used += _estimate_tokens(successes)

        built = "\n".join(parts)
        report['total_tokens'] = used
        report['budget'] = budget
        self.last_built = built
        self.last_tokens = used
        self.last_report = report
        self.last_hash = _hashlib.sha256(built.encode('utf-8')).hexdigest()[:16]
        return built

    def describe_last_build(self):
        """Human-readable diagnostic of the most recent context assembly."""
        report = getattr(self, 'last_report', None)
        if not report:
            return "No context has been built yet."

        kb = report.get('knowledge', {}) or {}
        pat = report.get('patterns', {}) or {}
        lines = [
            "CONTEXT INSPECTOR",
            "  Total injected : ~%d tokens (budget %d, num_ctx %d)"
            % (report.get('total_tokens', 0), report.get('budget', 0),
               Config.OLLAMA_NUM_CTX),
            "  Core rules     : ~%d tokens" % report.get('core_tokens', 0),
            "  Document state : ~%d tokens" % report.get('doc_tokens', 0),
            "",
            "  Search terms   : %s" % (", ".join(kb.get('terms', [])) or "(none)"),
            "  KB hits found  : %d   included: %d (~%d tokens)"
            % (kb.get('raw_hits', 0), kb.get('ranked_hits', 0), kb.get('used_tokens', 0)),
        ]
        if kb.get('note'):
            lines.append("  KB note        : %s" % kb['note'])
        lines += [
            "",
            "  Verified patterns available : %d" % pat.get('candidates', 0),
            "  Matched the prompt          : %d" % pat.get('scored', 0),
            "  Selection mode              : %s"
            % ("RECENCY FALLBACK (nothing matched)" if pat.get('fallback_recency')
               else "relevance-ranked"),
            "  Pattern tokens              : ~%d" % pat.get('used_tokens', 0),
        ]
        if kb.get('raw_hits', 0) == 0 and kb.get('terms'):
            lines += ["",
                      "  DIAGNOSIS: terms were extracted but the knowledge base "
                      "returned nothing.",
                      "  Check that Technical_Data loaded (show_tech_data_status()) "
                      "and that",
                      "  these terms exist as categories/keys in "
                      "FreeCAD_Knowledge_Base.json."]
        return "\n".join(lines)

    def stable_hash(self):
        """Hash of the INVARIANT part of the context (rules + verified
        knowledge), excluding live document state. Drives the Phase 8
        registration handshake: change the knowledge base and every agent's
        registration goes stale, forcing a re-read.

        NOTE: called with an empty prompt so it hashes the recency-ordered
        verified set, which is prompt-independent and therefore stable.
        """
        successes, _ = self.recent_successes(prompt="", limit=20, budget_tokens=99999)
        base = self.core_rules() + successes
        return _hashlib.sha256(base.encode('utf-8')).hexdigest()[:16]


_ollama_context_builder = OllamaContextBuilder()


def get_bridge_context_hash():
    """Module-level accessor used by the registration handshake."""
    try:
        return _ollama_context_builder.stable_hash()
    except Exception:
        return "unavailable"


# ============================================================
# PHASE 5 - CODE EXTRACTION, PRE-VALIDATION, SUBMISSION
# ============================================================

_CODE_FENCE_RE = re.compile(r"```(?:python|py)?\s*\n(.*?)```", re.DOTALL | re.IGNORECASE)
_THINK_RE = re.compile(r"<think>.*?</think>", re.DOTALL | re.IGNORECASE)


def extract_python_code(response_text):
    """Pull the executable command out of a model response.

    Returns (code, note). code is None when nothing usable was found.
    """
    if not response_text:
        return None, "empty response"

    # Defensive: strip reasoning blocks in case a reasoning model is swapped in
    text = _THINK_RE.sub('', response_text)

    blocks = _CODE_FENCE_RE.findall(text)
    if blocks:
        code = max(blocks, key=len).strip()
        if len(blocks) > 1:
            return code, "%d code blocks returned - using the largest" % len(blocks)
        return code, None

    # Fallback: unfenced but obviously code
    stripped = text.strip()
    code_markers = ('doc = App', 'import Part', 'App.ActiveDocument', 'Part.make')
    if any(marker in stripped for marker in code_markers):
        return stripped, "no code fence found - extracted heuristically, review carefully"

    return None, "no python code block in response"


def prevalidate_command(code):
    """Check model output against the sandbox rules BEFORE submission.

    Catching it here means the chat panel can say "the model tried to import
    os" instead of surfacing an opaque sandbox rejection three seconds later.
    Returns (ok, reason).
    """
    if not code or not code.strip():
        return False, "empty command"
    if len(code) > Config.MAX_COMMAND_LENGTH:
        return False, "command exceeds MAX_COMMAND_LENGTH (%d chars)" % Config.MAX_COMMAND_LENGTH

    for pattern in Config.FORBIDDEN_PATTERNS:
        if pattern in code:
            return False, "blocked pattern '%s' (sandbox would reject this)" % pattern

    if 'App.ActiveDocument' not in code and 'App.newDocument' not in code:
        return True, "WARNING: no document reference - fresh exec scope may NameError"

    return True, None


def submit_command_to_bridge(code, agent_id=None, context_hash=None, command_type='execute'):
    """Append a command to AI_INPUT_FILE as JSONL. Returns command_id or None.

    This is the ONLY route from Ollama into execution. Same file, same schema,
    same poll loop, same sandbox as Claude Code.
    """
    command_id = str(_uuid.uuid4())
    entry = {
        'id': command_id,
        'type': command_type,
        'command': code,
        'agent_id': agent_id or Config.OLLAMA_AGENT_ID,
        'timestamp': datetime.now().isoformat(),
    }
    if context_hash:
        entry['context_hash'] = context_hash

    try:
        with open(AI_INPUT_FILE, 'a', encoding='utf-8') as f:
            f.write(json.dumps(entry, ensure_ascii=False) + '\n')
            f.flush()
            os.fsync(f.fileno())   # reader is byte-position based; make sure it's on disk
        return command_id
    except Exception as e:
        App.Console.PrintError("[OLLAMA] Could not write command to bridge: %s\n" % e)
        return None


def submit_registration(agent_id=None):
    """Phase 8: send the 'hello' handshake through the normal command file."""
    return submit_command_to_bridge(
        code='', agent_id=agent_id or Config.OLLAMA_AGENT_ID,
        context_hash=get_bridge_context_hash(), command_type='hello')


# ============================================================
# PHASE 2 - PROVIDER-AGNOSTIC LLM CLIENT
# ============================================================

class LLMClient:
    """Chat client for Ollama (local) and OpenRouter (cloud).

    stdlib urllib only - no third-party packages inside FreeCAD's Python.
    Both providers collapse to the same interface: stream_chat() yields
    plain text deltas.
    """

    def __init__(self, provider=None, host=None, model=None, api_key=None):
        self.provider = provider or Config.OLLAMA_PROVIDER
        if self.provider == "openrouter":
            self.host = (host or Config.OPENROUTER_HOST).rstrip('/')
            self.model = model or Config.OPENROUTER_MODEL
            self.api_key = api_key or Config.OPENROUTER_API_KEY
        else:
            self.host = (host or Config.OLLAMA_HOST).rstrip('/')
            self.model = model or Config.OLLAMA_MODEL
            self.api_key = None
        self.last_error = None

    # -------------------- server lifecycle --------------------

    def is_server_running(self):
        if self.provider != "ollama":
            return True
        try:
            req = urllib.request.Request(self.host + "/api/tags")
            with urllib.request.urlopen(
                    req, timeout=Config.OLLAMA_CONNECT_TIMEOUT_SEC) as resp:
                return resp.status == 200
        except Exception:
            return False

    def list_models(self):
        if self.provider != "ollama":
            return [Config.OPENROUTER_MODEL]
        try:
            req = urllib.request.Request(self.host + "/api/tags")
            with urllib.request.urlopen(
                    req, timeout=Config.OLLAMA_CONNECT_TIMEOUT_SEC) as resp:
                data = json.loads(resp.read().decode('utf-8'))
            return [m.get('name', '') for m in data.get('models', []) if m.get('name')]
        except Exception as e:
            self.last_error = str(e)
            return []

    def ensure_server_running(self):
        """Start `ollama serve` on demand. Returns (ok, message). Never raises.
        Called from the WORKER thread - the sleep here is off the GUI thread."""
        if self.provider != "ollama":
            return True, "Cloud provider - no local server needed"
        if self.is_server_running():
            return True, "Server already running"
        if not Config.OLLAMA_AUTOSTART_SERVER:
            return False, "Server not reachable and autostart disabled"

        try:
            kwargs = {}
            if os.name == 'nt':
                kwargs['creationflags'] = 0x00000008 | 0x08000000  # detached, no window
            subprocess.Popen(
                ["ollama", "serve"],
                stdout=subprocess.DEVNULL, stderr=subprocess.DEVNULL, **kwargs)
        except FileNotFoundError:
            return False, "'ollama' not found on PATH - is Ollama installed?"
        except Exception as e:
            return False, "Could not launch ollama serve: %s" % e

        deadline = time.time() + Config.OLLAMA_SERVER_BOOT_WAIT_SEC
        while time.time() < deadline:
            if self.is_server_running():
                return True, "Server started"
            time.sleep(0.5)
        return False, "Server did not answer within %ss" % Config.OLLAMA_SERVER_BOOT_WAIT_SEC

    # -------------------- payload construction --------------------

    def _build_request(self, messages):
        if self.provider == "openrouter":
            url = self.host + "/v1/chat/completions"
            payload = {
                "model": self.model,
                "messages": messages,
                "stream": True,
                "temperature": Config.OLLAMA_TEMPERATURE,
                "top_p": Config.OLLAMA_TOP_P,
            }
            headers = {
                "Content-Type": "application/json",
                "Authorization": "Bearer %s" % (self.api_key or ""),
                "HTTP-Referer": "https://freecad.org",
                "X-Title": "FreeCAD AI Bridge",
            }
            wire = "sse"
        else:
            url = self.host + "/api/chat"
            payload = {
                "model": self.model,
                "messages": messages,
                "stream": True,
                "keep_alive": Config.OLLAMA_KEEP_ALIVE,
                "options": {
                    "num_ctx": Config.OLLAMA_NUM_CTX,   # MUST be explicit - see Config
                    "temperature": Config.OLLAMA_TEMPERATURE,
                    "top_p": Config.OLLAMA_TOP_P,
                },
            }
            headers = {"Content-Type": "application/json"}
            wire = "ndjson"

        data = json.dumps(payload).encode('utf-8')
        return urllib.request.Request(url, data=data, headers=headers, method="POST"), wire

    @staticmethod
    def _extract_delta(obj, wire):
        try:
            if wire == "ndjson":
                return (obj.get('message') or {}).get('content', '') or ''
            choices = obj.get('choices') or []
            if not choices:
                return ''
            return (choices[0].get('delta') or {}).get('content', '') or ''
        except Exception:
            return ''

    # -------------------- streaming --------------------

    def stream_chat(self, messages, cancel_cb=None):
        """Generator yielding text deltas. Raises RuntimeError with a
        human-readable message; the worker catches it and emits sig_error."""
        request, wire = self._build_request(messages)
        try:
            resp = urllib.request.urlopen(
                request, timeout=Config.OLLAMA_REQUEST_TIMEOUT_SEC)
        except urllib.error.HTTPError as e:
            body = ''
            try:
                body = e.read().decode('utf-8', 'replace')[:400]
            except Exception:
                pass
            raise RuntimeError("HTTP %s from %s: %s" % (e.code, self.provider, body))
        except urllib.error.URLError as e:
            raise RuntimeError("Cannot reach %s at %s (%s)"
                               % (self.provider, self.host, e.reason))
        except Exception as e:
            raise RuntimeError("Request failed: %s" % e)

        try:
            for raw in resp:
                if cancel_cb and cancel_cb():
                    break
                line = raw.decode('utf-8', 'replace').strip()
                if not line:
                    continue
                if wire == "sse":
                    if not line.startswith('data:'):
                        continue
                    line = line[5:].strip()
                    if line == '[DONE]':
                        break
                try:
                    obj = json.loads(line)
                except ValueError:
                    continue
                if obj.get('error'):
                    raise RuntimeError(str(obj['error']))
                delta = self._extract_delta(obj, wire)
                if delta:
                    yield delta
                if wire == "ndjson" and obj.get('done'):
                    break
        finally:
            try:
                resp.close()
            except Exception:
                pass


# ============================================================
# PHASE 3 - WORKER THREAD
# ============================================================

class OllamaWorker(QtCore.QThread):
    """Network-only worker. See contract note #3 at the top of this section.

    Nothing in run() may touch FreeCAD. Results cross back as Qt signals,
    which Qt automatically queues onto the GUI thread.
    """

    sig_token = QtCore.Signal(str)
    sig_finished = QtCore.Signal(str, float)
    sig_error = QtCore.Signal(str)
    sig_status = QtCore.Signal(str)

    def __init__(self, client, messages, parent=None):
        super(OllamaWorker, self).__init__(parent)
        self._client = client
        self._messages = messages
        self._cancel = False

    def cancel(self):
        self._cancel = True

    def _is_cancelled(self):
        return self._cancel

    def run(self):
        started = time.time()
        chunks = []
        try:
            self.sig_status.emit("Checking server...")
            ok, msg = self._client.ensure_server_running()
            if not ok:
                self.sig_error.emit(msg)
                return

            self.sig_status.emit("Generating...")
            for delta in self._client.stream_chat(self._messages, self._is_cancelled):
                chunks.append(delta)
                self.sig_token.emit(delta)

            self.sig_status.emit("Cancelled" if self._cancel else "Done")
            self.sig_finished.emit(''.join(chunks), time.time() - started)
        except Exception as e:
            # Never let an exception escape a QThread - it takes the process with it
            self.sig_error.emit(str(e))


# ============================================================
# PHASES 3/5/6/9 - CHAT PANEL
# ============================================================

# ===========================================================================
# The Bridge's tab pages, shared.
# ---------------------------------------------------------------------------
# These lived inside OllamaChatDialog until 4.0.01, which put them in a
# window the operator had no reason to open: the probe of a live 3.5.2
# session found AIAgentConfigDialog on screen with no tabs and no
# OllamaChatDialog in existence at all. They belong to whichever dialog
# wants them, so they live here and not in one of them.
# ===========================================================================
class _BridgeTabsMixin(object):

    def _assemble_tabs(self, first=None):
        """The dialog's real layout: five tabs over one donation block.

        `first` is (widget, title) for the host dialog's own page, so the
        same assembly serves any window that wants these tabs.
        """
        outer = QtWidgets.QVBoxLayout(self)
        outer.setContentsMargins(6, 6, 6, 4)

        self.tabs = QtWidgets.QTabWidget()
        # v4.0.02: the tabs were Qt's default grey and small. Imagineering
        # palette, 11pt bold, real padding, and the selected tab filled with
        # cyan so which page you are on is obvious at a glance.
        self.tabs.setStyleSheet(
            "QTabWidget::pane { border: 1px solid %s; border-radius: 6px;"
            " background: %s; top: -1px; }"
            "QTabBar { qproperty-drawBase: 0; }"
            "QTabBar::tab { background: %s; color: %s;"
            " border: 1px solid #3a3a4d; border-bottom: none;"
            " border-top-left-radius: 6px; border-top-right-radius: 6px;"
            " padding: 10px 24px; margin-right: 3px; min-width: 110px;"
            " font-size: 11pt; font-weight: bold; }"
            "QTabBar::tab:selected { background: %s; color: %s;"
            " border: 1px solid %s; border-bottom: none; }"
            "QTabBar::tab:hover:!selected { background: #35354d;"
            " color: %s; }"
            % (ACCENT_CYAN, BG_COLOR, CARD_COLOR, TEXT_COLOR,
               ACCENT_CYAN, BG_COLOR, ACCENT_CYAN, ACCENT_CYAN))
        def _scrolled(w):
            """Put a page in a scroll area.

            Without this a single tall page sets the whole window's
            minimum height -- Locations alone wanted 671, which is what
            made the declared 700 minimum unreachable and the window
            feel stuck. A page that does not fit should scroll, not
            push the window bigger than the screen.
            """
            sa = QtWidgets.QScrollArea()
            sa.setWidgetResizable(True)
            sa.setFrameShape(QtWidgets.QFrame.Shape.NoFrame)
            sa.setHorizontalScrollBarPolicy(
                QtCore.Qt.ScrollBarPolicy.ScrollBarAsNeeded)
            sa.setWidget(w)
            return sa

        if first is not None:
            self.tabs.addTab(_scrolled(first[0]), first[1])

        # Each page is built behind its own guard. A page that cannot be
        # built must not take the whole dialog -- and must say why, in the
        # tab, rather than quietly not being there.
        for title, builder in (("Project Log", self._build_log_tab),
                               ("Add IDE", self._build_ide_tab),
                               ("Locations", self._build_locations_tab),
                               ("Visual Capture", self._build_capture_tab),
                               # v5.0.05: "Mesh", not "Outsource" --
                               # the tab is named for the WORK, which is
                               # also the admission rule. One tab with a
                               # list inside it; the next mesh target
                               # does not add a tab here. The builder
                               # keeps its general name because the
                               # machinery is general.
                               ("Mesh", self._build_outsource_tab)):
            try:
                self.tabs.addTab(_scrolled(builder()), title)
            except BaseException as exc:
                page = QtWidgets.QWidget()
                lay = QtWidgets.QVBoxLayout(page)
                msg = QtWidgets.QLabel(
                    "This tab could not be built:\n\n%s: %s\n\nThe rest "
                    "of the Bridge is unaffected."
                    % (type(exc).__name__, exc))
                msg.setWordWrap(True)
                lay.addWidget(msg)
                lay.addStretch()
                self.tabs.addTab(page, title + " (failed)")
                App.Console.PrintWarning(
                    "[BRIDGE] %s tab could not be built: %s\n"
                    % (title, exc))

        outer.addWidget(self.tabs, stretch=1)

        sep = QtWidgets.QFrame()
        sep.setFrameShape(QtWidgets.QFrame.Shape.HLine)
        sep.setStyleSheet(
            "color: #00bcd4; background: #00bcd4; max-height: 1px;")
        # v4.0.15: the notice goes ABOVE the donation block and below
        # the tabs, so it is on screen whichever tab you are on, in every
        # window that assembles these tabs.
        try:
            outer.addWidget(self._build_notice())
        except BaseException as exc:
            App.Console.PrintWarning(
                "[BRIDGE] The notice could not be built: %s" % exc + chr(10))
        outer.addWidget(sep)
        outer.addWidget(DonationPanel())

    def _build_log_tab(self):
        """The real Project Log panel, hosted as a page.

        Not a button that opens a second window: the panel builds its own
        widgets into the page it is given. The reference is kept because the
        panel owns an 800 ms poll timer, and a panel that is garbage
        collected takes its timer with it.
        """
        page = QtWidgets.QWidget()
        self._log_panel = AIProjectLogPanel(host=page, show_donation=False)
        return page

    # ---- Add IDE -----------------------------------------------------
    def _build_ide_tab(self):
        """Which editors the Bridge can see, and how to add one it cannot.

        v4.0.12: the Name / Command / Full path / Arguments form is gone.
        Once the list shows everything, those fields only asked the
        operator to retype what was already on screen. Browsing for the
        executable answers all four questions at once.
        """
        page = QtWidgets.QWidget()
        lay = QtWidgets.QVBoxLayout(page)

        intro = QtWidgets.QLabel(
            "Editors the Bridge can see. Found automatically unless "
            "marked (yours). Detection looks for each editor's command on "
            "your PATH, then in its usual install folder -- one in "
            "neither is unknown, not broken, and Add an editor will "
            "register it.")
        intro.setWordWrap(True)
        lay.addWidget(intro)

        self.ide_list = QtWidgets.QListWidget()
        lay.addWidget(self.ide_list, stretch=1)

        btns = QtWidgets.QHBoxLayout()
        # v4.0.13: one button. "Set path..." used to sit beside this
        # one doing the same job with a different name, which is the same
        # redundancy as Start beside Connect. The selection decides.
        b_add = QtWidgets.QPushButton("Add / locate...")
        b_add.setToolTip(
            "Browse for the program. With a row selected it is located "
            "under that name; with nothing selected the name comes from "
            "the file.")
        b_add.setStyleSheet(_btn_style("#39ff14"))
        b_add.clicked.connect(self._ide_browse_add)

        b_test = QtWidgets.QPushButton("Test")
        b_test.setToolTip("Check whether the selected editor can be found")
        b_test.setStyleSheet(_btn_style("#4a9eff"))
        b_test.clicked.connect(self._ide_test)

        b_rem = QtWidgets.QPushButton("Remove")
        b_rem.setToolTip("Forget an editor you added")
        b_rem.setStyleSheet(_btn_style("#F4424D"))
        b_rem.clicked.connect(self._ide_remove)

        for b in (b_add, b_test, b_rem):
            btns.addWidget(b)
        btns.addStretch()
        lay.addLayout(btns)

        self.ide_status_msg = QtWidgets.QLabel("")
        self.ide_status_msg.setWordWrap(True)
        self.ide_status_msg.setStyleSheet("color: #00bcd4;")
        lay.addWidget(self.ide_status_msg)

        where = QtWidgets.QLabel("Stored in %s" % AI_CONFIG_FILE)
        where.setWordWrap(True)
        where.setStyleSheet(_path_style())
        lay.addWidget(where)

        self._refresh_ide_list()
        return page

    # -- helpers --------------------------------------------------------
    def _ide_selected(self):
        """(key, is_custom) for the selected row, or (None, False)."""
        it = self.ide_list.currentItem()
        if it is None:
            return None, False
        key = it.data(QtCore.Qt.ItemDataRole.UserRole)
        return key, str(key or "").startswith(
            IDEManager.CUSTOM_KEY_PREFIX)

    @staticmethod
    def _ide_pick_exe(parent, title):
        path, _ = QtWidgets.QFileDialog.getOpenFileName(
            parent, title, "", "Programs (*.exe *.cmd *.bat);;All (*)")
        return path

    def _ide_browse_add(self):
        """Browse for an executable and register it.

        v4.0.13: this also does what the separate "Set path..." button
        did, because they only ever differed in which name was used.
        A selected row lends its name -- so locating a not-found built-in
        fills in that row rather than creating a second one under a name
        derived from the filename.
        """
        key, _custom = self._ide_selected()
        known = IDEManager.all_ides().get(key or "", {}).get("name", "")
        title = ("Where is %s?" % known) if known \
            else "Choose the editor's program"
        path = self._ide_pick_exe(self, title)
        if not path:
            return
        path = os.path.normpath(path)
        if known:
            name = known
        else:
            name = os.path.splitext(os.path.basename(path))[0]
            name = name.replace("_", " ").replace("-", " ").strip().title()
        ok, msg = IDEManager.add_custom_ide(name, path=path)
        self.ide_status_msg.setText(msg)
        if ok:
            self._refresh_ide_list()


    def _ide_test(self):
        key, custom = self._ide_selected()
        if key is None:
            self.ide_status_msg.setText("Select an editor first.")
            return
        info = IDEManager.all_ides().get(key, {})
        found, where = IDEManager.probe(
            info.get("cli", ""), (info.get("paths_win") or [""])[0])
        if found:
            self.ide_status_msg.setText(
                "%s found at %s" % (info.get("name", key), where))
        else:
            self.ide_status_msg.setText(
                "%s was not found. Its command is not on your PATH and it "
                "is not where it usually installs. Use Set path to point "
                "at it." % info.get("name", key))

    def _ide_remove(self):
        key, custom = self._ide_selected()
        if key is None:
            self.ide_status_msg.setText("Select an editor first.")
            return
        if not custom:
            self.ide_status_msg.setText(
                "That one was found automatically, not added by you, so "
                "there is nothing to remove.")
            return
        ok, msg = IDEManager.remove_custom_ide(key)
        self.ide_status_msg.setText(msg)
        if ok:
            self._refresh_ide_list()

    def _refresh_ide_list(self):
        """Everything the Bridge can see, found or added."""
        self.ide_list.clear()
        try:
            detected = IDEManager.refresh_detection()
        except BaseException:
            detected = {}
        customs = IDEManager.load_custom_ides()
        every = IDEManager.all_ides()
        shown = 0

        for key in sorted(detected):
            if key in customs:
                continue
            info = detected[key]
            it = QtWidgets.QListWidgetItem(
                "%s  -  found at %s"
                % (info.get("name", key),
                   info.get("path", "") or info.get("source", "")))
            it.setData(QtCore.Qt.ItemDataRole.UserRole, key)
            self.ide_list.addItem(it)
            shown += 1

        for key in sorted(every):
            if key in detected or key in customs:
                continue
            if every[key].get("is_local_chat"):
                continue
            it = QtWidgets.QListWidgetItem(
                "%s  -  not on this machine" % every[key].get("name", key))
            it.setData(QtCore.Qt.ItemDataRole.UserRole, key)
            self.ide_list.addItem(it)
            shown += 1

        for key in sorted(customs):
            entry = customs[key]
            found, where = IDEManager.probe(
                entry.get("cli", ""), (entry.get("paths_win") or [""])[0])
            it = QtWidgets.QListWidgetItem(
                "%s  (yours)  -  %s"
                % (entry.get("name", key),
                   ("found at %s" % where) if found else "not found"))
            it.setData(QtCore.Qt.ItemDataRole.UserRole, key)
            self.ide_list.addItem(it)
            shown += 1

        if not shown:
            self.ide_list.addItem("(nothing found, and nothing added yet)")
        try:
            self.ide_status_msg.setText(
                "%d of %d editors found on this machine."
                % (len(detected), max(len(every) - 1, 1)))
        except BaseException:
            pass


    # ---- Locations ---------------------------------------------------
    # ---- Locations ---------------------------------------------------
    def _build_locations_tab(self):
        """Where the technical database and the learning files live.

        v4.0.11: lists, not single boxes. There is no reason a reference
        library has to be one folder, and the learning history was split
        across two databases with no way to use both.
        """
        page = QtWidgets.QWidget()
        lay = QtWidgets.QVBoxLayout(page)

        intro = QtWidgets.QLabel(
            "Each role can have several folders. The technical database "
            "is searched in order. For learning, the FIRST folder is the "
            "one written to and the rest are read as well, so an older "
            "history still counts. Empty means the worked-out default.")
        intro.setWordWrap(True)
        lay.addWidget(intro)

        self._loc_lists = {}
        for key, title, note in (
                ("library_dir", "Technical database (read only)",
                 "knowledge bases, references, the Python rules. Searched "
                 "in order; the first folder holding a file wins."),
                ("learning_dir", "AI learning and self-correction",
                 "the first is written to; the others are read too."),
                ("io_dir", "Bridge I/O",
                 "the command and result files. One only."),
        ):
            group = QtWidgets.QGroupBox(title)
            group.setStyleSheet(_group_style())
            gl = QtWidgets.QVBoxLayout(group)
            gl.setSpacing(6)
            hint = QtWidgets.QLabel(note)
            hint.setWordWrap(True)
            hint.setStyleSheet(_hint_style())
            gl.addWidget(hint)
            lst = QtWidgets.QListWidget()
            lst.setMaximumHeight(86)
            gl.addWidget(lst)
            row = QtWidgets.QHBoxLayout()
            b_add = QtWidgets.QPushButton("Add...")
            b_add.setStyleSheet(_btn_style("#39ff14"))
            b_add.clicked.connect(
                lambda _=False, k=key: self._loc_add(k))
            b_forget = QtWidgets.QPushButton("Forget")
            b_forget.setStyleSheet(_btn_style("#F4424D"))
            b_forget.clicked.connect(
                lambda _=False, k=key: self._loc_forget(k))
            b_up = QtWidgets.QPushButton("Make first")
            b_up.setToolTip("For learning, the first folder is the one "
                            "written to.")
            b_up.setStyleSheet(_btn_style("#00bcd4"))
            b_up.clicked.connect(
                lambda _=False, k=key: self._loc_promote(k))
            for b in (b_add, b_forget, b_up):
                row.addWidget(b)
            row.addStretch()
            gl.addLayout(row)
            lay.addWidget(group)
            self._loc_lists[key] = lst

        btns = QtWidgets.QHBoxLayout()
        b_check = QtWidgets.QPushButton("Check what is there")
        b_check.setStyleSheet(_btn_style("#4a9eff"))
        b_check.clicked.connect(self._loc_refresh)
        b_reset = QtWidgets.QPushButton("Back to defaults")
        b_reset.setStyleSheet(_btn_style("#ffb300"))
        b_reset.clicked.connect(self._loc_reset)
        btns.addWidget(b_check)
        btns.addWidget(b_reset)
        btns.addStretch()
        lay.addLayout(btns)

        self.loc_status = QtWidgets.QLabel("")
        self.loc_status.setWordWrap(True)
        self.loc_status.setStyleSheet("color: #00bcd4;")
        lay.addWidget(self.loc_status)
        lay.addStretch()

        self._loc_marks = {}
        self._loc_refresh()
        return page

    # -- the list is the setting ---------------------------------------
    def _loc_paths(self, key):
        return [self._loc_lists[key].item(i).data(
                    QtCore.Qt.ItemDataRole.UserRole)
                for i in range(self._loc_lists[key].count())
                if self._loc_lists[key].item(i).data(
                    QtCore.Qt.ItemDataRole.UserRole)]

    def _loc_store(self, key, paths):
        ok, msg = _cfg_set(key, [p for p in paths if p])
        if not ok:
            self.loc_status.setText(msg)
        self._loc_refresh()

    def _loc_add(self, key):
        d = QtWidgets.QFileDialog.getExistingDirectory(
            self, "Add a folder for %s" % key)
        if not d:
            return
        d = os.path.normpath(d)
        cur = self._loc_paths(key)
        if key == "io_dir":
            cur = [d]           # the Bridge has one I/O directory
        elif os.path.normcase(d) in [os.path.normcase(x) for x in cur]:
            self.loc_status.setText("That folder is already listed.")
            return
        else:
            cur.append(d)
        self._loc_store(key, cur)

    def _loc_forget(self, key):
        it = self._loc_lists[key].currentItem()
        if it is None:
            self.loc_status.setText("Select a folder to forget first.")
            return
        gone = it.data(QtCore.Qt.ItemDataRole.UserRole)
        self._loc_store(key, [p for p in self._loc_paths(key) if p != gone])
        self.loc_status.setText("Forgot %s" % gone)

    def _loc_promote(self, key):
        it = self._loc_lists[key].currentItem()
        if it is None:
            self.loc_status.setText("Select a folder first.")
            return
        p = it.data(QtCore.Qt.ItemDataRole.UserRole)
        rest = [x for x in self._loc_paths(key) if x != p]
        self._loc_store(key, [p] + rest)

    def _loc_reset(self):
        for key in self._loc_lists:
            _cfg_set(key, "")
        self._loc_marks = {}
        self.loc_status.setText("Back to the worked-out defaults.")
        self._loc_refresh()

    # -- what is there, and what changed -------------------------------
    @staticmethod
    def _loc_fingerprint(path):
        """Enough to notice a change without walking a huge tree: how many
        entries, and the newest modification time, one level down."""
        try:
            names = os.listdir(path)
            newest = 0.0
            for nm in names:
                try:
                    newest = max(newest,
                                 os.path.getmtime(os.path.join(path, nm)))
                except BaseException:
                    pass
            return (len(names), int(newest))
        except BaseException:
            return None

    @staticmethod
    def _loc_entries(path):
        try:
            if not os.path.isfile(path):
                return None
            with open(path, "r", encoding="utf-8") as fh:
                db = json.load(fh) or {}
            return sum(len(db.get(k) or [])
                       for k in ("successful_patterns", "error_resolutions",
                                 "critical_patterns", "command_templates",
                                 "common_mistakes"))
        except BaseException:
            return None

    def _loc_refresh(self):
        live = {"library_dir": library_dirs(),
                "learning_dir": [LEARNING_DIR] + _cfg_list("learning_dir")[1:],
                "io_dir": [AI_IO_DIR]}
        probe = {
            "library_dir": ("FreeCAD_Knowledge_Base.json",
                            "AI_Bridge_Python_Rules.txt",
                            "Expressions_Reference.txt"),
            "learning_dir": ("AI_Learning_Database.json",),
            "io_dir": ("ai_status.json", "ai_input_commands.jsonl"),
        }
        changed, summary = [], []
        for key, lst in self._loc_lists.items():
            lst.clear()
            seen = []
            for i, path in enumerate(live.get(key, [])):
                if not path or path in seen:
                    continue
                seen.append(path)
                bits = []
                if key == "learning_dir":
                    bits.append("WRITTEN" if i == 0 else "read only")
                if os.path.isdir(path):
                    here = [f for f in probe[key]
                            if os.path.isfile(os.path.join(path, f))]
                    bits.append("%d/%d files" % (len(here), len(probe[key])))
                    if key == "learning_dir":
                        e = self._loc_entries(
                            os.path.join(path, "AI_Learning_Database.json"))
                        bits.append("%s entries"
                                    % ("no" if e is None else e))
                    fp = self._loc_fingerprint(path)
                    was = self._loc_marks.get(path)
                    if was is not None and fp != was:
                        bits.append("CHANGED since last check")
                        changed.append(os.path.basename(path) or path)
                    self._loc_marks[path] = fp
                else:
                    bits.append("does not exist")
                if not _cfg_list(key):
                    bits.append("default")
                it = QtWidgets.QListWidgetItem(
                    "%s    [%s]" % (path, ", ".join(bits)))
                it.setData(QtCore.Qt.ItemDataRole.UserRole, path)
                lst.addItem(it)
            summary.append("%s %d" % (key.replace("_dir", ""), len(seen)))
        try:
            self.loc_status.setText(
                "Checked at %s  -  %s.%s"
                % (time.strftime("%H:%M:%S"), ",  ".join(summary),
                   ("  Changed: " + ", ".join(changed)) if changed
                   else "  Nothing changed since the last check."))
        except BaseException:
            pass

    def _build_capture_tab(self):
        """Screenshots for a model an agent cannot otherwise make sense
        of -- rendered by a SECOND FreeCAD process, so the operator's
        session never stalls for them.

        Nothing happens until Capture is pressed. Images cost tokens to
        read and nobody should be billed for them by surprise.
        """
        page = QtWidgets.QWidget()
        lay = QtWidgets.QVBoxLayout(page)

        intro = QtWidgets.QLabel(
            "Slice the model and photograph it, so an image-capable AI can "
            "see what the measurements do not explain. Each slice shows the "
            "section outline at that plane in white, with every other "
            "plane's outline behind it in cyan and ahead of it in amber, "
            "out to the bounding box -- a contour map of the shape along "
            "that axis, not just a cutaway. Runs in its own FreeCAD "
            "process -- this session carries on."
        )
        intro.setWordWrap(True)
        lay.addWidget(intro)

        self.cap_info = QtWidgets.QLabel("")
        self.cap_info.setWordWrap(True)
        lay.addWidget(self.cap_info)

        form = QtWidgets.QFormLayout()

        # v4.0.19: fidelity in DECADES, not a bundled "Detail" preset.
        # The preset hardcoded an absolute mesh deviation, so the same
        # word meant a blob on a 5 mm part and a memory bomb on a 10 m
        # structure. This is the decade of the smallest detail worth
        # seeing, and it sets the mesh AND the grid you read the section
        # against.
        self.cap_fidelity = QtWidgets.QComboBox()
        for val, label in CAPTURE_FIDELITY:
            self.cap_fidelity.addItem(label, val)
        self.cap_fidelity.setCurrentIndex(0)
        self.cap_fidelity.setToolTip(
            "The smallest detail worth seeing. Sets the mesh deviation "
            "and the grid pitch, so the grid is always a round decade you "
            "can measure a section against. If the decade cannot suit "
            "this model it is stepped and the reason is reported.")
        form.addRow("Fidelity", self.cap_fidelity)

        # Separate control, because token cost is not a geometry question.
        self.cap_size = QtWidgets.QComboBox()
        for w, h in ((800, 600), (1024, 768), (1600, 1200), (2048, 1536)):
            self.cap_size.addItem("%d x %d" % (w, h), (w, h))
        self.cap_size.setCurrentIndex(1)
        self.cap_size.setToolTip(
            "Bigger images read more clearly and cost more tokens. The "
            "frame follows the subject's own proportions, so this is the "
            "longer side, not a fixed shape.")
        form.addRow("Image size", self.cap_size)

        self.cap_slices = QtWidgets.QSpinBox()
        self.cap_slices.setRange(1, 400)
        self.cap_slices.setValue(12)
        self.cap_slices.setToolTip(
            "Sections through the model. Measured at about 56 ms each, "
            "so this is cheap -- the preset only sets a starting point.")
        form.addRow("Slices", self.cap_slices)

        # v4.0.10: all three, not one of three. A single family of
        # parallel sections is a stack of outlines; three orthogonal
        # families let something rebuild the shape. All start ticked, so
        # the question is which to leave out.
        axrow = QtWidgets.QWidget()
        axl = QtWidgets.QHBoxLayout(axrow)
        axl.setContentsMargins(0, 0, 0, 0)
        self.cap_axes = {}
        for key, lbl in (("x", "X  side to side"),
                         ("y", "Y  front to back"),
                         ("z", "Z  top to bottom")):
            cb = QtWidgets.QCheckBox(lbl)
            cb.setChecked(True)
            self.cap_axes[key] = cb
            axl.addWidget(cb)
        axl.addStretch()
        form.addRow("Slice along", axrow)
        lay.addLayout(form)

        # v4.0.10: pick parts from the tree. Capture used to be the whole
        # document or nothing.
        lay.addWidget(QtWidgets.QLabel(
            "Parts to capture. Tick none for the whole document:"))
        self.cap_items = QtWidgets.QListWidget()
        # v4.0.19: no height cap. This was setMaximumHeight(130) -- about
        # five rows -- which is a letterbox on any real assembly. It now
        # takes every pixel the tab can spare.
        self.cap_items.setMinimumHeight(200)
        self.cap_items.setVerticalScrollBarPolicy(
            QtCore.Qt.ScrollBarPolicy.ScrollBarAlwaysOn)
        self.cap_items.setHorizontalScrollBarPolicy(
            QtCore.Qt.ScrollBarPolicy.ScrollBarAsNeeded)
        # Hundreds of rows scroll smoothly only if Qt may assume one row
        # height instead of measuring every item.
        self.cap_items.setUniformItemSizes(True)
        self.cap_items.setSelectionMode(
            QtWidgets.QAbstractItemView.SelectionMode.ExtendedSelection)
        lay.addWidget(self.cap_items, stretch=1)
        pickrow = QtWidgets.QHBoxLayout()
        b_sel = QtWidgets.QPushButton("Use tree selection")
        b_sel.setToolTip("Tick whatever is selected in FreeCAD's tree")
        b_sel.setStyleSheet(_btn_style("#00bcd4"))
        b_sel.clicked.connect(self._cap_from_selection)
        b_none = QtWidgets.QPushButton("Clear")
        b_none.setStyleSheet(_btn_style("#9e9e9e"))
        b_none.clicked.connect(self._cap_clear_picks)
        pickrow.addWidget(b_sel)
        pickrow.addWidget(b_none)
        pickrow.addStretch()
        lay.addLayout(pickrow)

        self.cap_second = QtWidgets.QCheckBox(
            "Second-degree slicing: after the first pass, cut again "
            "where the section changes most")
        self.cap_second.setToolTip(
            "The first pass measures how many parts and regions each "
            "plane crosses. Where that changes fastest is where geometry "
            "starts, stops or splits -- the places a coarse pass misses. "
            "No input needed; it is computed from the first pass.")
        lay.addWidget(self.cap_second)

        warn = QtWidgets.QLabel(
            "Images are expensive to READ: roughly 1,000 to 1,600 tokens "
            "each for a vision model. Making them is cheap and costs you "
            "nothing until an agent looks at them.")
        warn.setWordWrap(True)
        warn.setStyleSheet("color: #ffb300;")
        lay.addWidget(warn)

        btns = QtWidgets.QHBoxLayout()
        b_ref = QtWidgets.QPushButton("Measure document")
        b_ref.setStyleSheet(_btn_style("#4a9eff"))
        b_ref.clicked.connect(self._capture_refresh)
        b_cap = QtWidgets.QPushButton("Capture")
        b_cap.setStyleSheet(_btn_style("#39ff14"))
        b_cap.clicked.connect(self._capture_shoot)
        b_open = QtWidgets.QPushButton("Open folder")
        b_open.setStyleSheet(_btn_style("#00bcd4"))
        b_open.clicked.connect(self._capture_open)
        for b in (b_ref, b_cap, b_open):
            btns.addWidget(b)
        btns.addStretch()
        lay.addLayout(btns)

        self.cap_status = QtWidgets.QLabel("")
        self.cap_status.setWordWrap(True)
        self.cap_status.setStyleSheet("color: #00bcd4;")
        lay.addWidget(self.cap_status)
        # No addStretch() here any more: it and the parts list were both
        # asking for the leftover height, and padding was winning.

        self._cap_dir = ""
        self._cap_poll = None
        self._capture_refresh()
        return page

    def _cap_fill_items(self):
        """List the document's solids, each with a tick box."""
        try:
            self.cap_items.clear()
            doc = App.ActiveDocument
            if doc is None:
                return
            rows, _notes = measure_solids(doc)
            for r in rows:
                label = r.get("label") or r["name"]
                txt = "%s  (%s)" % (label, _fmt_vol(r["volume"]))
                if label != r["name"]:
                    txt += "   [%s]" % r["name"]
                it = QtWidgets.QListWidgetItem(txt)
                it.setFlags(it.flags()
                            | QtCore.Qt.ItemFlag.ItemIsUserCheckable)
                it.setCheckState(QtCore.Qt.CheckState.Unchecked)
                it.setData(QtCore.Qt.ItemDataRole.UserRole, r["name"])
                self.cap_items.addItem(it)
        except BaseException as exc:
            App.Console.PrintWarning(
                "[CAPTURE] Could not list the parts: %s\n" % exc)

    def _cap_picked(self):
        out = []
        for i in range(self.cap_items.count()):
            it = self.cap_items.item(i)
            if it.checkState() == QtCore.Qt.CheckState.Checked:
                out.append(it.data(QtCore.Qt.ItemDataRole.UserRole))
        return out

    def _cap_from_selection(self):
        """Tick whatever the operator has selected in FreeCAD's tree."""
        try:
            names = set(o.Name for o in Gui.Selection.getSelection())
            if not names:
                self.cap_status.setText("Nothing is selected in the tree.")
                return
            hit = 0
            for i in range(self.cap_items.count()):
                it = self.cap_items.item(i)
                on = it.data(QtCore.Qt.ItemDataRole.UserRole) in names
                it.setCheckState(QtCore.Qt.CheckState.Checked if on
                                 else QtCore.Qt.CheckState.Unchecked)
                hit += 1 if on else 0
            self.cap_status.setText(
                "%d of %d selected objects are capturable solids."
                % (hit, len(names)))
        except BaseException as exc:
            self.cap_status.setText("Could not read the selection: %s" % exc)

    def _cap_clear_picks(self):
        for i in range(self.cap_items.count()):
            self.cap_items.item(i).setCheckState(
                QtCore.Qt.CheckState.Unchecked)
        self.cap_status.setText("Cleared - the whole document will be used.")


    def _capture_open(self):
        try:
            d = self._cap_dir or log_dir_path(App.ActiveDocument)
            if os.path.isdir(d):
                webbrowser.open("file:///" + d.replace(os.sep, "/"))
            else:
                self.cap_status.setText("Nothing captured yet.")
        except BaseException as exc:
            self.cap_status.setText("Could not open it: %s" % exc)

    def _capture_refresh(self):
        """Report the real extent, from the log's own inventory."""
        doc = App.ActiveDocument
        if doc is None:
            self.cap_info.setText("No document open.")
            return
        try:
            rows, notes = measure_solids(doc)
            tot = solid_totals(rows)
            if tot["bbox"] is None:
                self.cap_info.setText(
                    "%s has no measurable solid to photograph."
                    % doc.Label)
                return
            bb = tot["bbox"]
            self.cap_info.setText(
                "%s: %d parts, %s x %s x %s."
                % (doc.Label, tot["count"], _fmt_len(bb[3] - bb[0]),
                   _fmt_len(bb[4] - bb[1]), _fmt_len(bb[5] - bb[2])))
            self._cap_fill_items()
        except BaseException as exc:
            self.cap_info.setText("Could not measure: %s" % exc)

    def _capture_shoot(self):
        """Launch the worker and poll for its manifest."""
        doc = App.ActiveDocument
        if doc is None:
            self.cap_status.setText("No document open.")
            return
        try:
            out = os.path.join(log_dir_path(doc), "views")
        except BaseException as exc:
            self.cap_status.setText(
                "Save the document first -- there is nowhere to put the "
                "images (%s)." % exc)
            return
        axes = [k for k, cb in self.cap_axes.items() if cb.isChecked()]
        if not axes:
            self.cap_status.setText(
                "Tick at least one axis. All three is what lets an agent "
                "rebuild the shape rather than only look at it.")
            return
        picks = self._cap_picked()
        w, h = self.cap_size.currentData() or (1024, 768)
        ok, msg, d = start_capture(
            doc, out,
            slices=self.cap_slices.value(),
            axes=axes, objects=picks,
            second_degree=self.cap_second.isChecked(),
            fidelity=self.cap_fidelity.currentData() or 0.0,
            width=w, height=h)
        if ok:
            msg += ("  %d axes x %d slices, %s."
                    % (len(axes), self.cap_slices.value(),
                       ("%d parts" % len(picks)) if picks
                       else "whole document"))
        self.cap_status.setText(msg)
        if not ok:
            return
        self._cap_dir = d
        self._cap_t0 = time.time()
        if self._cap_poll is None:
            self._cap_poll = QtCore.QTimer()
            self._cap_poll.setInterval(700)
            self._cap_poll.timeout.connect(self._capture_poll)
        self._cap_poll.start()

    def _capture_poll(self):
        """Watch for the manifest. Polling a file is how the rest of the
        Bridge talks to other processes, and it needs no IPC."""
        try:
            man = os.path.join(self._cap_dir, "capture_manifest.json")
            waited = time.time() - getattr(self, "_cap_t0", 0)
            if not os.path.exists(man):
                if waited > 300:
                    self._cap_poll.stop()
                    self.cap_status.setText(
                        "The capture process has not reported in five "
                        "minutes. Check %s" % self._cap_dir)
                else:
                    self.cap_status.setText(
                        "Capturing... %.0f s (separate process; this "
                        "session is free)" % waited)
                return
            self._cap_poll.stop()
            with open(man, "r", encoding="utf-8") as fh:
                m = json.load(fh)
            if m.get("status") != "ok":
                self.cap_status.setText(
                    "Capture failed (%s). Details in %s"
                    % (m.get("status"), man))
                return
            imgs = m.get("images", [])
            extra = m.get("second_degree", [])
            # The grid pitch is the whole reason the images are
            # measurable, so it goes in the sentence the operator reads --
            # not only into the manifest.
            g = m.get("grid_mm")
            pitch = ""
            if g:
                pitch = ("  Grid %s, so a section can be measured off the "
                         "image."
                         % ("%g mm" % g if g < 1000
                            else ("%g m" % (g / 1000.0) if g < 1000000
                                  else "%g km" % (g / 1000000.0))))
                if m.get("fidelity_note"):
                    pitch += "  (%s)" % m["fidelity_note"]
            self.cap_status.setText(
                "%d images in %.1f s, %s. %s%s"
                % (len(imgs), m.get("seconds", 0), self._cap_dir,
                   ("%d chosen by the second pass at %s"
                    % (len(extra),
                       ", ".join(str(e["at"]) for e in extra)))
                   if extra else "No second pass.", pitch))
            log = LOGS.get(App.ActiveDocument.Name) \
                if App.ActiveDocument is not None else None
            if log is not None:
                log.entry("views",
                          "capture at the operator's request: %d images "
                          "in %s\nEach costs roughly 1,000 to 1,600 "
                          "tokens for an agent to read."
                          % (len(imgs), self._cap_dir))
        except BaseException as exc:
            try:
                self._cap_poll.stop()
            except BaseException:
                pass
            self.cap_status.setText("Capture poll failed: %s" % exc)

    def _build_notice(self):
        """The disclaimer, and the one button that acts on it.

        Not a tab and not dismissible: it is the condition of using this,
        so it sits under whichever tab you are on.
        """
        box = QtWidgets.QFrame()
        box.setStyleSheet(
            "QFrame { background: #2a2a1d; border: 1px solid #ffb300;"
            " border-radius: 6px; }")
        lay = QtWidgets.QHBoxLayout(box)
        lay.setContentsMargins(10, 7, 10, 7)

        words = QtWidgets.QLabel(
            "<b style='color:#ffb300;'>AI can make mistakes.</b> "
            "<span style='color:#e0e0e0;'>Neither the author of this macro "
            "nor any AI you enlist through it is responsible for your "
            "document &mdash; you are. Back up and fork your work daily at "
            "a minimum, and before anything you would hate to redo.</span>")
        words.setWordWrap(True)
        words.setTextFormat(QtCore.Qt.TextFormat.RichText)
        lay.addWidget(words, stretch=1)

        side = QtWidgets.QVBoxLayout()
        self.fork_btn = QtWidgets.QPushButton("Back up && fork now")
        self.fork_btn.setToolTip(
            "Save this document, then write a dated numbered copy into a "
            "Forks folder beside it. You stay in the file you are in.")
        self.fork_btn.setStyleSheet(_btn_style("#ffb300"))
        self.fork_btn.clicked.connect(self._fork_clicked)
        side.addWidget(self.fork_btn)
        self.fork_msg = QtWidgets.QLabel("")
        self.fork_msg.setWordWrap(True)
        self.fork_msg.setStyleSheet(_hint_style())
        self.fork_msg.setMinimumWidth(250)
        side.addWidget(self.fork_msg)
        lay.addLayout(side)

        self._refresh_fork()
        return box

    def _fork_clicked(self):
        ok, msg, _path = do_fork(App.ActiveDocument)
        self.fork_msg.setText(msg)
        self.fork_msg.setStyleSheet(
            _hint_style("#39ff14" if ok else "#F4424D"))
        App.Console.PrintMessage("[BRIDGE] %s" % msg + chr(10))

    def _refresh_fork(self):
        """Say where the fork state stands.

        v5.0.15: this really IS called from the display timer now. Until
        then it ran once at construction and never again, so the line
        froze at whatever was true when the window opened -- it was
        still reporting "no document" with a document open in front of
        it. Cheap and never raises, because it runs twice a second.
        """
        try:
            st = fork_state(App.ActiveDocument)
            due = bool(st.get("due"))
            self.fork_msg.setText(
                ("DUE: %s" if due else "%s") % st.get("why", ""))
            self.fork_msg.setStyleSheet(
                _hint_style("#ffb300" if due else None)
                + (" font-weight: bold;" if due else ""))
        except BaseException:
            pass

    # ---- Outsource ---------------------------------------------------
    def _build_outsource_tab(self):
        """Other programs, driven from here -- ONE page for all of them.

        A list on the left and a detail pane on the right, not a tab each.
        The tab bar has a 110 px minimum per tab, so a dozen targets would
        simply scroll off the top of the window; and four location rows
        hand-written per target is the Start-beside-Connect mistake at
        twenty-eight controls. A target is a dict in OUTSOURCE_TARGETS,
        and this renders whatever is in it.
        """
        page = QtWidgets.QWidget()
        lay = QtWidgets.QVBoxLayout(page)

        intro = QtWidgets.QLabel(
            "Mesh work, sent to the program that is better at it than "
            "FreeCAD, and brought back. A mesh is what a scan arrives as "
            "and what FreeCAD handles worst -- and turning one into a "
            "solid is how an agent gets at INTERNAL geometry, which no "
            "outside view of a part will show it. Each target does its "
            "real work in its OWN process, so this session stays "
            "responsive, and each keeps four locations of its own: data "
            "out, data in, its agent training, and its agent database.")
        intro.setWordWrap(True)
        lay.addWidget(intro)

        split = QtWidgets.QHBoxLayout()

        self.os_list = QtWidgets.QListWidget()
        self.os_list.setMinimumWidth(190)
        self.os_list.setMaximumWidth(260)
        self.os_list.setVerticalScrollBarPolicy(
            QtCore.Qt.ScrollBarPolicy.ScrollBarAlwaysOn)
        self.os_list.setUniformItemSizes(True)
        split.addWidget(self.os_list)

        self.os_stack = QtWidgets.QStackedWidget()
        self._os_pages = {}
        for t in OUTSOURCE_TARGETS:
            try:
                w = self._outsource_page(t)
            except BaseException as exc:
                w = QtWidgets.QWidget()
                wl = QtWidgets.QVBoxLayout(w)
                m = QtWidgets.QLabel(
                    "This target's page could not be built:  %s: %s\n\n"
                    "The rest of the Bridge is unaffected."
                    % (type(exc).__name__, exc))
                m.setWordWrap(True)
                wl.addWidget(m)
                wl.addStretch()
                App.Console.PrintWarning(
                    "[OUTSOURCE] %s page failed: %s"
                    % (t.get("name"), exc) + chr(10))
            self._os_pages[t["key"]] = self.os_stack.addWidget(w)
            it = QtWidgets.QListWidgetItem(t.get("name", t["key"]))
            it.setData(QtCore.Qt.ItemDataRole.UserRole, t["key"])
            self.os_list.addItem(it)
        split.addWidget(self.os_stack, stretch=1)
        lay.addLayout(split, stretch=1)

        self.os_list.currentRowChanged.connect(self.os_stack.setCurrentIndex)
        if OUTSOURCE_TARGETS:
            self.os_list.setCurrentRow(0)

        self.os_status = QtWidgets.QLabel("")
        self.os_status.setWordWrap(True)
        self.os_status.setStyleSheet("color: #00bcd4;")
        lay.addWidget(self.os_status)

        self._outsource_refresh()
        return page

    def _outsource_page(self, t):
        """One target: the credit, the three steps, and nothing else on
        screen until it is asked for.

        v5.0.09: this page had grown to nineteen buttons and four
        paragraphs of warning text, which is a reference card, not a
        tool. The work is three steps -- send the mesh, open the
        program, bring the result back -- so those are the page. The
        five folders, the licence and the privacy notes are all still
        here, one click away, because they matter when they matter and
        are noise the rest of the time.
        """
        key = t["key"]
        w = QtWidgets.QWidget()
        lay = QtWidgets.QVBoxLayout(w)
        lay.setContentsMargins(4, 0, 4, 0)
        lay.setSpacing(8)

        # -- who made it, in one line ---------------------------------
        head = QtWidgets.QLabel(
            "<b style='color:#00bcd4;font-size:13pt;'>%s</b>"
            "<br><span style='color:#c3cad6;'>by %s</span>"
            "<span style='color:#aab3c2;'> &nbsp;&middot;&nbsp; %s</span>"
            % (t.get("name", key), t.get("author", "its authors"),
               t.get("licence", "")))
        head.setTextFormat(QtCore.Qt.TextFormat.RichText)
        head.setWordWrap(True)
        lay.addWidget(head)

        what = QtWidgets.QLabel(t.get("short", t.get("what", "")))
        what.setWordWrap(True)
        lay.addWidget(what)

        # -- the three steps ------------------------------------------
        proc = QtWidgets.QGroupBox("The process")
        proc.setStyleSheet(_group_style())
        pl = QtWidgets.QVBoxLayout(proc)
        pl.setSpacing(8)

        for num, title, hint, label, colour, slot in (
                (1, "Send the mesh out",
                 "Exports what you have selected, or the whole document "
                 "if nothing is.",
                 "Push selection", "#39ff14", "push"),
                (2, "Work on it there",
                 "", "Open %s" % t.get("name", key), "#4a9eff", "open"),
                (3, "Bring the result back",
                 "Imports anything new it has left for you. Pressing it "
                 "twice will not duplicate.",
                 "Pull new results", "#ffb300", "pull")):
            row = QtWidgets.QHBoxLayout()
            n_lab = QtWidgets.QLabel(
                "<span style='color:#00bcd4;font-size:14pt;"
                "font-weight:bold;'>%d</span>" % num)
            n_lab.setTextFormat(QtCore.Qt.TextFormat.RichText)
            n_lab.setFixedWidth(22)
            row.addWidget(n_lab)

            col = QtWidgets.QVBoxLayout()
            col.setSpacing(1)
            ttl = QtWidgets.QLabel("<b>%s</b>" % title)
            ttl.setTextFormat(QtCore.Qt.TextFormat.RichText)
            col.addWidget(ttl)
            sub = QtWidgets.QLabel(hint)
            sub.setWordWrap(True)
            sub.setStyleSheet(_hint_style())
            col.addWidget(sub)
            # Step 2's line is not fixed text: it is the live route, so
            # "Open ScanRuler" says underneath it whether that means the
            # website or this machine, and whether it needs a connection.
            if slot == "open":
                setattr(self, "_os_reach_%s" % key, sub)
            row.addLayout(col, stretch=1)

            btn = QtWidgets.QPushButton(label)
            btn.setMinimumWidth(170)
            btn.setStyleSheet(_btn_style(colour))
            if slot == "push":
                btn.clicked.connect(
                    lambda _=False, k=key: self._outsource_push(k))
            elif slot == "open":
                btn.clicked.connect(
                    lambda _=False, k=key: self._outsource_launch(k))
            else:
                btn.clicked.connect(
                    lambda _=False, k=key: self._outsource_pull(k))
            row.addWidget(btn)
            pl.addLayout(row)

        msg = QtWidgets.QLabel("")
        msg.setWordWrap(True)
        msg.setStyleSheet(_hint_style(ACCENT_CYAN))
        setattr(self, "_os_msg_%s" % key, msg)
        pl.addWidget(msg)
        lay.addWidget(proc)

        # -- everything else, folded away -----------------------------
        more = QtWidgets.QPushButton("Folders, licence and privacy")
        more.setCheckable(True)
        more.setChecked(False)
        more.setStyleSheet(_btn_style("#9e9e9e"))
        lay.addWidget(more, alignment=QtCore.Qt.AlignmentFlag.AlignLeft)

        drawer = QtWidgets.QWidget()
        dl = QtWidgets.QVBoxLayout(drawer)
        dl.setContentsMargins(0, 0, 0, 0)
        drawer.setVisible(False)
        more.toggled.connect(drawer.setVisible)

        locs = QtWidgets.QGroupBox("Locations  -  each one independent")
        locs.setStyleSheet(_group_style())
        gl = QtWidgets.QVBoxLayout(locs)
        for slot, title, hint in (
                ("root", "Its own folder",
                 "where the program lives; found automatically if it can be"),
                ("push", "Data OUT of FreeCAD", t.get("push_what", "")),
                ("pull", "Data IN to FreeCAD", t.get("pull_what", "")),
                ("training", "Agent training (.md)",
                 "what an agent should read before driving this target"),
                ("db", "Agent database",
                 "what this target has learned, and what has been pulled")):
            gl.addLayout(self._outsource_loc_row(key, slot, title, hint))
        dl.addWidget(locs)

        small = QtWidgets.QGroupBox("Licence, privacy and offline")
        small.setStyleSheet(_group_style())
        sl = QtWidgets.QVBoxLayout(small)
        for text, colour in (
                ("Credit: " + t.get("credit", ""), None),
                (("Licence %s. %s" % (t.get("licence", "?"),
                                      t.get("licence_note", "")))
                 if t.get("licence") else "", "#ffb300"),
                (t.get("offline", ""), "#ffb300"),
                (t.get("privacy", ""), "#ffb300"),
                (("To run it locally: needs %s, then  %s  in its folder."
                  % (t.get("needs", "its toolchain"),
                     "  &  ".join(t.get("build") or [])))
                 if t.get("build") else "", None)):
            if not text:
                continue
            q = QtWidgets.QLabel(text)
            q.setWordWrap(True)
            q.setStyleSheet(_hint_style(colour))
            sl.addWidget(q)
        b_repo = QtWidgets.QPushButton("Open the repo")
        b_repo.setToolTip(t.get("repo", ""))
        b_repo.setStyleSheet(_btn_style("#9e9e9e"))
        b_repo.clicked.connect(
            lambda _=False, k=key: self._outsource_open_repo(k))
        sl.addWidget(b_repo, alignment=QtCore.Qt.AlignmentFlag.AlignLeft)
        dl.addWidget(small)

        lay.addWidget(drawer)
        lay.addStretch()
        return w

    def _outsource_loc_row(self, key, slot, title, hint):
        row = QtWidgets.QHBoxLayout()
        lab = QtWidgets.QLabel("%s:" % title)
        lab.setMinimumWidth(150)
        lab.setToolTip(hint)
        row.addWidget(lab)
        val = QtWidgets.QLineEdit()
        val.setReadOnly(True)
        val.setStyleSheet(_path_style())
        row.addWidget(val, stretch=1)
        setattr(self, "_os_%s_%s" % (slot, key), val)
        b = QtWidgets.QPushButton("Set...")
        b.setMaximumWidth(64)
        b.setStyleSheet(_btn_style("#00bcd4"))
        b.clicked.connect(
            lambda _=False, k=key, s=slot: self._outsource_set(k, s))
        row.addWidget(b)
        o = QtWidgets.QPushButton("Open")
        o.setMaximumWidth(64)
        o.setStyleSheet(_btn_style("#9e9e9e"))
        o.clicked.connect(
            lambda _=False, k=key, s=slot: self._outsource_open(k, s))
        row.addWidget(o)
        f = QtWidgets.QPushButton("Default")
        f.setMaximumWidth(78)
        f.setToolTip("Forget what is set here and go back to the "
                     "worked-out default")
        f.setStyleSheet(_btn_style("#F4424D"))
        f.clicked.connect(
            lambda _=False, k=key, s=slot: self._outsource_forget(k, s))
        row.addWidget(f)
        return row

    # -- handlers -------------------------------------------------------
    def _outsource_current(self):
        it = self.os_list.currentItem()
        if it is None:
            return None
        return outsource_target(it.data(QtCore.Qt.ItemDataRole.UserRole))

    def _outsource_say(self, key, text):
        m = getattr(self, "_os_msg_%s" % key, None)
        if m is not None:
            m.setText(text)
        self.os_status.setText(text)

    def _outsource_set(self, key, slot):
        t = outsource_target(key)
        if t is None:
            return
        if slot == "training":
            path, _ = QtWidgets.QFileDialog.getOpenFileName(
                self, "Agent training for %s" % t["name"], "",
                "Markdown (*.md);;All (*)")
        elif slot == "db":
            path, _ = QtWidgets.QFileDialog.getSaveFileName(
                self, "Agent database for %s" % t["name"], "",
                "JSON (*.json);;All (*)")
        else:
            path = QtWidgets.QFileDialog.getExistingDirectory(
                self, "%s for %s" % (slot, t["name"]))
        if not path:
            return
        ok, msg = _cfg_set("outsource.%s.%s" % (key, slot),
                           os.path.normpath(path))
        self._outsource_say(key, msg if not ok else
                            "%s set to %s" % (slot, os.path.normpath(path)))
        self._outsource_refresh()

    def _outsource_forget(self, key, slot):
        _cfg_set("outsource.%s.%s" % (key, slot), "")
        self._outsource_say(key, "%s is back to the default." % slot)
        self._outsource_refresh()

    def _outsource_open(self, key, slot):
        t = outsource_target(key)
        if t is None:
            return
        p = outsource_paths(t).get(slot, "")
        if not p:
            self._outsource_say(
                key, "There is no %s for %s yet -- use Set." % (slot, key))
            return
        target = p if os.path.isdir(p) else os.path.dirname(p)
        try:
            os.makedirs(target, exist_ok=True)
            QtGui.QDesktopServices.openUrl(
                QtCore.QUrl.fromLocalFile(target))
            self._outsource_say(key, "Opened %s" % target)
        except BaseException as exc:
            self._outsource_say(key, "Could not open %s: %s" % (target, exc))

    def _outsource_launch(self, key):
        """Open the target itself. The launcher decides website or local;
        this only reports what it did."""
        t = outsource_target(key)
        if t is None:
            return
        ok, msg, url = outsource_launch(t)
        if ok and url:
            QtGui.QDesktopServices.openUrl(QtCore.QUrl(url))
        self._outsource_say(key, msg)
        App.Console.PrintMessage("[OUTSOURCE] %s" % msg + chr(10))
        self._outsource_refresh()

    def _outsource_open_repo(self, key):
        t = outsource_target(key)
        if t is None or not t.get("repo"):
            return
        QtGui.QDesktopServices.openUrl(QtCore.QUrl(t["repo"]))
        self._outsource_say(key, "Opened %s" % t["repo"])

    def _outsource_push(self, key):
        t = outsource_target(key)
        if t is None:
            return
        try:
            picked = [o.Name for o in Gui.Selection.getSelection()]
        except BaseException:
            picked = []
        ok, msg, _path = outsource_push(t, App.ActiveDocument, picked)
        self._outsource_say(key, msg)
        App.Console.PrintMessage("[OUTSOURCE] %s" % msg + chr(10))

    def _outsource_pull(self, key):
        t = outsource_target(key)
        if t is None:
            return
        ok, msg, _got = outsource_pull(t, App.ActiveDocument)
        self._outsource_say(key, msg)
        App.Console.PrintMessage("[OUTSOURCE] %s" % msg + chr(10))
        self._outsource_refresh()

    def _outsource_refresh(self):
        """Fill every target's rows and say where each one stands. Cheap,
        and must never raise -- it runs when the tab is built."""
        try:
            for t in OUTSOURCE_TARGETS:
                key = t["key"]
                p = outsource_paths(t)
                st = outsource_state(t)
                for slot in ("root", "push", "pull", "training", "db"):
                    box = getattr(self, "_os_%s_%s" % (slot, key), None)
                    if box is None:
                        continue
                    v = p.get(slot, "")
                    set_here = bool(_cfg_get("outsource.%s.%s" % (key, slot),
                                             ""))
                    exists = bool(v) and os.path.exists(v)
                    box.setText(
                        "%s    [%s%s]"
                        % (v or "(not found)",
                           "yours" if set_here else "default",
                           "" if exists else ", does not exist yet"))
                lab = getattr(self, "_os_reach_%s" % key, None)
                if lab is not None:
                    bits = ["ready via: %s%s"
                            % (st["ready"] or "nothing",
                               "  (needs the internet)"
                               if st["ready"] == "website" else
                               "  (works offline)"
                               if st["ready"] == "local" else "")]
                    bits.append(st["why"])
                    if st["mcp"]:
                        bits.append("MCP server: %s" % st["mcp"])
                    if st["training"]:
                        bits.append("training %s"
                                    % ("found" if st["training_found"]
                                       else "NOT found"))
                    lab.setText("   -   ".join(b for b in bits if b))
            cur = self._outsource_current()
            if cur is not None:
                self.os_status.setText(
                    "%d target%s. %s: %s"
                    % (len(OUTSOURCE_TARGETS),
                       "" if len(OUTSOURCE_TARGETS) == 1 else "s",
                       cur["name"], outsource_state(cur)["why"]))
        except BaseException:
            pass


class OllamaChatDialog(_BridgeTabsMixin, QtWidgets.QDialog):
    """Ollama chat panel: generate -> review -> submit -> auto-repair.

    LIVENESS: the heartbeat spinner in the status bar ticks every 100ms off
    the Qt event loop. If it ever stops during a generation, the thread
    boundary is broken - that is the standing acceptance test for this panel.
    """

    def __init__(self, parent=None):
        super(OllamaChatDialog, self).__init__(parent)
        self.setWindowTitle("Ollama - Local AI  |  AI Bridge v%s" % Config.VERSION)
        self.setMinimumSize(820, 760)
        self.setWindowFlags(self.windowFlags() | Qt.Window)

        self.client = LLMClient()
        self.context_builder = _ollama_context_builder
        self.worker = None
        self.history = []
        self.pending_code = None
        self.pending_command_id = None
        self.last_submitted_code = None
        self.repair_attempts = 0
        self.session_stats = {'sent': 0, 'ok': 0, 'failed': 0, 'repairs': 0}
        self.registered = False
        self._output_offset = 0
        self._heartbeat_frames = "|/-\\"
        self._heartbeat_index = 0

        self.setStyleSheet(
            "QDialog { background: %s; color: %s; }"
            "QLabel { color: %s; }"
            "QCheckBox { color: %s; }"
            "QPushButton { background: %s; color: %s;"
            " border: 1px solid %s; border-radius: 4px; padding: 6px 14px;"
            " min-height: 28px; font-weight: bold; }"
            "QPushButton:hover { background: %s; color: %s; }"
            "QPushButton:disabled { color: #666; border-color: #444; }"
            "QComboBox { background: %s; color: %s; padding: 4px; }"
            % (BG_COLOR, TEXT_COLOR, TEXT_COLOR, TEXT_COLOR, CARD_COLOR,
               TEXT_COLOR, ACCENT_BLUE, ACCENT_CYAN, BG_COLOR, CARD_COLOR, TEXT_COLOR)
        )

        self.setup_ui()
        self.refresh_models()
        self.reset_history()

        # Phase 6: tail AI_OUTPUT_FILE for results addressed to us
        self._seek_output_end()
        self.result_timer = QtCore.QTimer(self)
        self.result_timer.timeout.connect(self.poll_results)
        self.result_timer.start(1000)

        self.heartbeat = QtCore.QTimer(self)
        self.heartbeat.timeout.connect(self._tick_heartbeat)
        self.heartbeat.start(Config.OLLAMA_HEARTBEAT_MS)

        # Phase 8: register before anything can be executed
        QtCore.QTimer.singleShot(200, self.register_with_bridge)

    # -------------------- UI --------------------

    def setup_ui(self):
        # v4.0.01: back to building straight onto the dialog. 3.5.0 made this
        # a tab page, but the three tabs beside it have moved to the main
        # Bridge window -- the one that stays open -- so there is nothing
        # left here to tab between.
        layout = QtWidgets.QVBoxLayout(self)

        layout.addWidget(GradientLogoLabel("Imαgineering", 22),
                         alignment=Qt.AlignHCenter)
        subtitle = QtWidgets.QLabel("Ollama — Local AI Agent")
        subtitle.setAlignment(Qt.AlignCenter)
        subtitle.setStyleSheet(
            "color: %s; font-size: 13px; font-weight: bold;" % ACCENT_CYAN)
        layout.addWidget(subtitle)

        # ---- model row ----
        model_row = QtWidgets.QHBoxLayout()
        model_row.addWidget(QtWidgets.QLabel("Model:"))
        self.model_combo = QtWidgets.QComboBox()
        self.model_combo.setMinimumWidth(240)
        self.model_combo.currentTextChanged.connect(self._model_changed)
        model_row.addWidget(self.model_combo)

        refresh_btn = QtWidgets.QPushButton("Refresh")
        refresh_btn.clicked.connect(self.refresh_models)
        model_row.addWidget(refresh_btn)

        self.server_label = QtWidgets.QLabel("Server: unknown")
        self.server_label.setStyleSheet("padding: 5px; font-size: 9pt;")
        model_row.addWidget(self.server_label)

        self.reg_label = QtWidgets.QLabel("Registration: pending")
        self.reg_label.setStyleSheet("padding: 5px; font-size: 9pt; color: #ff9800;")
        model_row.addWidget(self.reg_label)
        model_row.addStretch()
        layout.addLayout(model_row)

        # ---- transcript ----
        self.transcript = QtWidgets.QTextEdit()
        self.transcript.setReadOnly(True)
        self.transcript.setStyleSheet(
            "font-family: 'Consolas', monospace; font-size: 10pt;"
            "background-color: %s; color: %s; border: 1px solid %s;"
            % (BG_COLOR, TEXT_COLOR, ACCENT_BLUE))
        self.transcript.setPlaceholderText("Ask Ollama for FreeCAD Python...")
        layout.addWidget(self.transcript, stretch=3)

        # ---- extracted code review pane (Phase 5) ----
        code_group = QtWidgets.QGroupBox("Extracted Command (review before execution)")
        code_group.setStyleSheet("QGroupBox { font-weight: bold; font-size: 10pt; }")
        code_layout = QtWidgets.QVBoxLayout()

        self.code_view = QtWidgets.QTextEdit()
        self.code_view.setMaximumHeight(160)
        self.code_view.setStyleSheet(
            "font-family: 'Consolas', monospace; font-size: 10pt;"
            "background-color: %s; color: %s; border: 1px solid %s;"
            % (CARD_COLOR, ACCENT_GREEN, ACCENT_BLUE))
        self.code_view.setPlaceholderText("Extracted code appears here — editable before sending.")
        code_layout.addWidget(self.code_view)

        code_btns = QtWidgets.QHBoxLayout()
        self.submit_btn = QtWidgets.QPushButton("Send to Bridge")
        self.submit_btn.setStyleSheet(
            "QPushButton { background: transparent; color: %s;"
            " border: 2px solid %s; border-radius: 4px; font-weight: bold; min-height: 28px; }"
            "QPushButton:hover { background: %s; color: %s; }"
            % (ACCENT_GREEN, ACCENT_GREEN, ACCENT_GREEN, BG_COLOR))
        self.submit_btn.setEnabled(False)
        self.submit_btn.clicked.connect(self.submit_clicked)
        code_btns.addWidget(self.submit_btn)

        self.discard_btn = QtWidgets.QPushButton("Discard")
        self.discard_btn.setEnabled(False)
        self.discard_btn.clicked.connect(self.discard_clicked)
        code_btns.addWidget(self.discard_btn)

        self.promote_btn = QtWidgets.QPushButton("Mark Verified")
        self.promote_btn.setToolTip(
            "Promote the last successful command to a VERIFIED pattern so it "
            "can be fed back to future agents. Only do this after checking the "
            "geometry is actually correct.")
        self.promote_btn.setEnabled(False)
        self.promote_btn.clicked.connect(self.promote_clicked)
        code_btns.addWidget(self.promote_btn)

        self.auto_exec_check = QtWidgets.QCheckBox("Auto-execute")
        self.auto_exec_check.setChecked(bool(Config.OLLAMA_AUTO_EXECUTE))
        self.auto_exec_check.setToolTip(
            "Submit generated code without review. Off by default — a local "
            "model produces plenty of code that runs fine while being wrong.")
        code_btns.addWidget(self.auto_exec_check)

        code_btns.addStretch()
        code_layout.addLayout(code_btns)
        code_group.setLayout(code_layout)
        layout.addWidget(code_group)

        # ---- prompt ----
        self.prompt = QtWidgets.QTextEdit()
        self.prompt.setMaximumHeight(80)
        self.prompt.setStyleSheet(
            "font-family: 'Consolas', monospace; font-size: 10pt;"
            "background-color: %s; color: %s; border: 1px solid %s;"
            % (CARD_COLOR, TEXT_COLOR, ACCENT_BLUE))
        self.prompt.setPlaceholderText("Describe what you want built... (Ctrl+Enter to send)")
        layout.addWidget(self.prompt)

        # ---- buttons ----
        btn_row = QtWidgets.QHBoxLayout()
        self.send_btn = QtWidgets.QPushButton("Send")
        self.send_btn.setStyleSheet(
            "QPushButton { background: transparent; color: %s;"
            " border: 2px solid %s; border-radius: 4px; padding: 6px 18px;"
            " font-weight: bold; min-height: 28px; }"
            "QPushButton:hover { background: %s; color: %s; }"
            % (ACCENT_GREEN, ACCENT_GREEN, ACCENT_GREEN, BG_COLOR))
        self.send_btn.clicked.connect(self.send_clicked)
        btn_row.addWidget(self.send_btn)

        self.stop_btn = QtWidgets.QPushButton("Stop")
        self.stop_btn.setStyleSheet(
            "QPushButton { background: transparent; color: %s;"
            " border: 2px solid %s; border-radius: 4px; padding: 6px 18px;"
            " font-weight: bold; min-height: 28px; }"
            "QPushButton:hover { background: %s; color: %s; }"
            % (CANCEL_RED, CANCEL_RED, CANCEL_RED, BG_COLOR))
        self.stop_btn.setEnabled(False)
        self.stop_btn.clicked.connect(self.stop_clicked)
        btn_row.addWidget(self.stop_btn)

        clear_btn = QtWidgets.QPushButton("Clear")
        clear_btn.clicked.connect(self.clear_clicked)
        btn_row.addWidget(clear_btn)

        self_test_btn = QtWidgets.QPushButton("Self Test")
        self_test_btn.setToolTip("Run the Ollama integration test suite (Phase 10)")
        self_test_btn.clicked.connect(self.self_test_clicked)
        btn_row.addWidget(self_test_btn)

        context_btn = QtWidgets.QPushButton("Context")
        context_btn.setToolTip(
            "Show exactly what knowledge was injected into the last message, "
            "which search terms were used, and how many knowledge-base hits "
            "came back. Use this when the token count looks too low.")
        context_btn.clicked.connect(self.context_clicked)
        btn_row.addWidget(context_btn)

        btn_row.addStretch()

        close_btn = QtWidgets.QPushButton("Close")
        close_btn.clicked.connect(self.close)
        btn_row.addWidget(close_btn)
        layout.addLayout(btn_row)

        # ---- status bar (heartbeat lives here) ----
        status_row = QtWidgets.QHBoxLayout()
        self.heartbeat_label = QtWidgets.QLabel("|")
        self.heartbeat_label.setStyleSheet(
            "color: %s; font-family: monospace; font-weight: bold; padding: 4px;"
            % ACCENT_GREEN)
        self.heartbeat_label.setToolTip(
            "GUI heartbeat. If this stops ticking, the event loop is blocked.")
        status_row.addWidget(self.heartbeat_label)

        self.status_label = QtWidgets.QLabel("Idle")
        self.status_label.setStyleSheet("padding: 4px; font-size: 9pt;")
        status_row.addWidget(self.status_label)
        status_row.addStretch()

        self.metrics_label = QtWidgets.QLabel("")
        self.metrics_label.setStyleSheet("padding: 4px; font-size: 9pt; color: #9aa0b0;")
        status_row.addWidget(self.metrics_label)
        layout.addLayout(status_row)

        # v4.0.01: Support & Donation, as on every other window in the suite.
        _sep = QtWidgets.QFrame()
        _sep.setFrameShape(QtWidgets.QFrame.Shape.HLine)
        _sep.setStyleSheet(
            "color: #00bcd4; background: #00bcd4; max-height: 1px;")
        layout.addWidget(_sep)
        layout.addWidget(DonationPanel())

    # -------------------- v3.5.0 tabs --------------------

    # ---- the standing notice ----------------------------------------

    # ---- Project Log -------------------------------------------------

    # ---- Add IDE -----------------------------------------------------







    # ---- Locations ---------------------------------------------------






    # ---- Visual Capture ----------------------------------------------




    # -------------------- helpers --------------------

    def _tick_heartbeat(self):
        self._heartbeat_index = (self._heartbeat_index + 1) % len(self._heartbeat_frames)
        self.heartbeat_label.setText(self._heartbeat_frames[self._heartbeat_index])

    def _model_changed(self, text):
        if text:
            self.client.model = text

    @staticmethod
    def _escape(text):
        return (str(text).replace('&', '&amp;').replace('<', '&lt;')
                .replace('>', '&gt;').replace('\n', '<br>'))

    def _append(self, html):
        self.transcript.moveCursor(QtGui.QTextCursor.End)
        self.transcript.insertHtml(html)
        self.transcript.moveCursor(QtGui.QTextCursor.End)
        self.transcript.ensureCursorVisible()

    def _update_metrics(self):
        stats = self.session_stats
        self.metrics_label.setText(
            "sent %d | ok %d | failed %d | repairs %d | ctx %d tok"
            % (stats['sent'], stats['ok'], stats['failed'], stats['repairs'],
               self.context_builder.last_tokens))

    def reset_history(self):
        """Rebuild the system prompt from current bridge knowledge (GUI thread)."""
        system_prompt = self.context_builder.build("")
        self.history = [{"role": "system", "content": system_prompt}]

    def refresh_models(self):
        running = self.client.is_server_running()
        if running:
            self.server_label.setText("Server: online")
            self.server_label.setStyleSheet(
                "padding: 5px; font-size: 9pt; color: %s; font-weight: bold;" % ACCENT_GREEN)
        else:
            self.server_label.setText("Server: offline (autostarts on Send)")
            self.server_label.setStyleSheet("padding: 5px; font-size: 9pt; color: #ff9800;")

        models = self.client.list_models()
        self.model_combo.blockSignals(True)
        self.model_combo.clear()
        if models:
            self.model_combo.addItems(models)
            index = self.model_combo.findText(Config.OLLAMA_MODEL)
            self.model_combo.setCurrentIndex(index if index >= 0 else 0)
        else:
            self.model_combo.addItem(Config.OLLAMA_MODEL)
        self.client.model = self.model_combo.currentText()
        self.model_combo.blockSignals(False)

    # -------------------- Phase 8: registration --------------------

    def register_with_bridge(self):
        """Send the 'hello' handshake. Execution stays locked until the
        bridge acknowledges - same gate every other agent passes through."""
        global _ai_monitor_timer
        if not _state.monitoring_active:
            self.reg_label.setText("Registration: bridge not monitoring")
            self.reg_label.setStyleSheet("padding: 5px; font-size: 9pt; color: %s;" % CANCEL_RED)
            self._append(
                "<span style='color:%s'>[BRIDGE] Monitoring is not running — press "
                "Start in the AI Bridge window, then Refresh here.</span><br>" % CANCEL_RED)
            return
        submit_registration()
        self.reg_label.setText("Registration: sent...")

    def _mark_registered(self):
        self.registered = True
        self.reg_label.setText("Registration: OK")
        self.reg_label.setStyleSheet(
            "padding: 5px; font-size: 9pt; color: %s; font-weight: bold;" % ACCENT_GREEN)

    # -------------------- generation --------------------

    def send_clicked(self):
        global _ollama_generating

        if self.worker is not None and self.worker.isRunning():
            return
        text = self.prompt.toPlainText().strip()
        if not text:
            return

        self.prompt.clear()
        self.repair_attempts = 0

        # Rebuild the system prompt against the CURRENT document + knowledge.
        # GUI thread only - this reads the live document.
        self.history[0] = {"role": "system", "content": self.context_builder.build(text)}
        self.history.append({"role": "user", "content": text})

        self._append("<br><b><span style='color:%s'>You:</span></b><br>%s<br>"
                     % (ACCENT_CYAN, self._escape(text)))
        self._start_generation()

    def _start_generation(self):
        global _ollama_generating

        self._append("<br><b><span style='color:%s'>Ollama:</span></b><br>" % ACCENT_GREEN)
        self.send_btn.setEnabled(False)
        self.stop_btn.setEnabled(True)
        self.status_label.setText("Starting...")

        # Flag set on the GUI thread only - keeps the v3.3.3 watchdog from
        # mistaking an off-thread generation for a GUI-thread freeze.
        _ollama_generating = True

        self.worker = OllamaWorker(self.client, list(self.history), self)
        self.worker.sig_token.connect(self.on_token)
        self.worker.sig_finished.connect(self.on_finished)
        self.worker.sig_error.connect(self.on_error)
        self.worker.sig_status.connect(self.status_label.setText)
        self.worker.start()

    def stop_clicked(self):
        if self.worker is not None and self.worker.isRunning():
            self.worker.cancel()
            self.status_label.setText("Cancelling...")

    def clear_clicked(self):
        self.transcript.clear()
        self.code_view.clear()
        self.reset_history()
        self.pending_code = None
        self.repair_attempts = 0
        self.submit_btn.setEnabled(False)
        self.discard_btn.setEnabled(False)
        self.status_label.setText("Idle")

    # -------------------- worker signal handlers (GUI thread) --------------------

    def on_token(self, delta):
        self.transcript.moveCursor(QtGui.QTextCursor.End)
        self.transcript.insertPlainText(delta)
        self.transcript.ensureCursorVisible()

    def on_finished(self, full_text, elapsed):
        global _ollama_generating
        _ollama_generating = False

        if full_text:
            self.history.append({"role": "assistant", "content": full_text})

        approx = _estimate_tokens(full_text)
        rate = (approx / elapsed) if elapsed > 0 else 0
        self.status_label.setText("Done — %.1fs, ~%.1f tok/s" % (elapsed, rate))
        self._append("<br>")
        self.send_btn.setEnabled(True)
        self.stop_btn.setEnabled(False)

        # Phase 5: extract, pre-validate, offer for review
        code, note = extract_python_code(full_text)
        if not code:
            self._append("<span style='color:#ff9800'>[EXTRACT] %s</span><br>"
                         % self._escape(note or 'no code found'))
            self._update_metrics()
            return
        if note:
            self._append("<span style='color:#ff9800'>[EXTRACT] %s</span><br>"
                         % self._escape(note))

        ok, reason = prevalidate_command(code)
        if not ok:
            self._append("<span style='color:%s'>[REJECTED PRE-SUBMISSION] %s</span><br>"
                         % (CANCEL_RED, self._escape(reason)))
            self.code_view.setPlainText(code)
            self.submit_btn.setEnabled(False)
            self.discard_btn.setEnabled(True)
            self._update_metrics()
            return
        if reason:
            self._append("<span style='color:#ff9800'>[CHECK] %s</span><br>"
                         % self._escape(reason))

        self.pending_code = code
        self.code_view.setPlainText(code)
        self.submit_btn.setEnabled(True)
        self.discard_btn.setEnabled(True)
        self._update_metrics()

        if self.auto_exec_check.isChecked():
            self.submit_clicked()

    def on_error(self, message):
        global _ollama_generating
        _ollama_generating = False

        self._append("<br><span style='color:%s'><b>[ERROR]</b> %s</span><br>"
                     % (CANCEL_RED, self._escape(message)))
        self.status_label.setText("Error")
        self.send_btn.setEnabled(True)
        self.stop_btn.setEnabled(False)
        App.Console.PrintError("[OLLAMA] %s\n" % message)

    # -------------------- Phase 5: submission --------------------

    def submit_clicked(self):
        code = self.code_view.toPlainText().strip()   # honour manual edits
        if not code:
            return
        if not self.registered:
            self._append("<span style='color:%s'>[BRIDGE] Not registered yet — "
                         "the bridge will reject this. Press Refresh / restart "
                         "monitoring.</span><br>" % CANCEL_RED)
            return

        ok, reason = prevalidate_command(code)
        if not ok:
            self._append("<span style='color:%s'>[BLOCKED] %s</span><br>"
                         % (CANCEL_RED, self._escape(reason)))
            return

        command_id = submit_command_to_bridge(
            code, agent_id=Config.OLLAMA_AGENT_ID,
            context_hash=get_bridge_context_hash())
        if not command_id:
            self._append("<span style='color:%s'>[BRIDGE] Submission failed</span><br>"
                         % CANCEL_RED)
            return

        self.pending_command_id = command_id
        self.last_submitted_code = code
        self.session_stats['sent'] += 1
        self.submit_btn.setEnabled(False)
        self.status_label.setText("Submitted — awaiting bridge result...")
        self._append("<span style='color:%s'>[BRIDGE] Submitted %s — awaiting result</span><br>"
                     % (ACCENT_CYAN, command_id[:8]))
        self._update_metrics()

    def discard_clicked(self):
        self.pending_code = None
        self.code_view.clear()
        self.submit_btn.setEnabled(False)
        self.discard_btn.setEnabled(False)

    def promote_clicked(self):
        """Phase 7: mark the last successful command as a VERIFIED pattern."""
        global _learning_system
        if not self.last_submitted_code or not _learning_system:
            return
        try:
            promoted = _learning_system.promote_pattern(self.last_submitted_code)
        except Exception as e:
            self._append("<span style='color:%s'>[PROMOTE] %s</span><br>"
                         % (CANCEL_RED, self._escape(e)))
            return
        if promoted:
            self._append("<span style='color:%s'>[PROMOTE] Pattern marked verified — "
                         "it can now be fed to future agents.</span><br>" % ACCENT_GREEN)
            self.promote_btn.setEnabled(False)
        else:
            self._append("<span style='color:#ff9800'>[PROMOTE] Pattern not found "
                         "in the learning database.</span><br>")

    # -------------------- Phase 6: result watching + auto-repair --------------------

    def _seek_output_end(self):
        """Start tailing from the current end of file - ignore history."""
        try:
            if os.path.exists(AI_OUTPUT_FILE):
                self._output_offset = os.path.getsize(AI_OUTPUT_FILE)
        except Exception:
            self._output_offset = 0

    def poll_results(self):
        """Tail AI_OUTPUT_FILE for entries addressed to Ollama."""
        try:
            if not os.path.exists(AI_OUTPUT_FILE):
                return
            size = os.path.getsize(AI_OUTPUT_FILE)
            if size < self._output_offset:
                self._output_offset = 0      # file was rotated
            if size == self._output_offset:
                return

            with open(AI_OUTPUT_FILE, 'r', encoding='utf-8') as f:
                f.seek(self._output_offset)
                lines = f.readlines()
                self._output_offset = f.tell()
        except (PermissionError, OSError):
            return          # locked this tick - retry next second, never stall
        except Exception:
            return

        for line in lines:
            line = line.strip()
            if not line:
                continue
            try:
                entry = json.loads(line)
            except ValueError:
                continue

            # AI_OUTPUT_FILE carries TWO envelope shapes and we must read both:
            #   write_output()        -> {'type','content':{...},'metadata'}  (command_result, error_report)
            #   flush_result_buffer() -> the payload dict FLAT at top level    (pong, registration_ack)
            # Missing the flat shape means registration_ack is never seen and
            # the panel stays locked out forever.
            content = entry.get('content')
            if not isinstance(content, dict):
                content = entry
            if not isinstance(content, dict):
                continue
            if content.get('agent_id') != Config.OLLAMA_AGENT_ID:
                continue
            self._handle_result(content)

    def _handle_result(self, content):
        ctype = content.get('type', '')

        if ctype == 'registration_ack':
            self._mark_registered()
            return

        if ctype == 'registration_required':
            self.registered = False
            self.reg_label.setText("Registration: stale — re-registering")
            self.reg_label.setStyleSheet("padding: 5px; font-size: 9pt; color: #ff9800;")
            submit_registration()
            return

        cid = content.get('command_id')
        if cid and self.pending_command_id and cid != self.pending_command_id:
            return

        if ctype == 'command_result' and content.get('success'):
            self.session_stats['ok'] += 1
            self.pending_command_id = None
            self.repair_attempts = 0
            self.status_label.setText("Executed OK")
            stdout = content.get('stdout')
            self._append("<span style='color:%s'>[BRIDGE] Command executed successfully"
                         "</span><br>" % ACCENT_GREEN)
            if stdout:
                self._append("<pre style='color:#9aa0b0'>%s</pre>"
                             % self._escape(str(stdout)[:800]))
            self.promote_btn.setEnabled(True)
            self._update_metrics()
            return

        if ctype in ('error_report_requires_ai_intervention', 'error_report'):
            self.session_stats['failed'] += 1
            self.pending_command_id = None
            details = content.get('error_details') or {}
            error_msg = details.get('error_message', 'unknown error')
            self._append("<span style='color:%s'>[BRIDGE] Execution failed: %s</span><br>"
                         % (CANCEL_RED, self._escape(error_msg)))
            self._update_metrics()
            self._attempt_repair(content)

    def _attempt_repair(self, error_report):
        """Feed the bridge's comprehensive error report straight back to the model.

        This is the highest-value part of the integration: a weak model with
        one grounded repair attempt beats a weak model one-shotting, by a lot.
        """
        if self.repair_attempts >= Config.OLLAMA_MAX_REPAIR_ATTEMPTS:
            self._append("<span style='color:#ff9800'>[REPAIR] Attempt limit (%d) "
                         "reached — stopping. Over to you.</span><br>"
                         % Config.OLLAMA_MAX_REPAIR_ATTEMPTS)
            return
        if self.worker is not None and self.worker.isRunning():
            return

        self.repair_attempts += 1
        self.session_stats['repairs'] += 1

        details = error_report.get('error_details') or {}
        suggestions = error_report.get('learning_database_suggestions') or []
        tech_refs = error_report.get('technical_documentation_references') or []

        parts = [
            "Your command FAILED. Fix it and return corrected code only.",
            "",
            "FAILED COMMAND:",
            str(error_report.get('original_command', ''))[:2000],
            "",
            "ERROR: %s" % details.get('error_message', 'unknown'),
        ]
        errors = details.get('console_errors') or []
        if errors:
            parts += ["", "CONSOLE ERRORS:", "\n".join(str(e) for e in errors[:5])]
        if suggestions:
            parts += ["", "KNOWN SOLUTIONS FROM THIS BRIDGE'S LEARNING DATABASE:"]
            for s in suggestions[:3]:
                parts.append("- %s -> %s" % (s.get('similar_error', ''),
                                             s.get('previous_solution', '')))
        if tech_refs:
            parts += ["", "RELEVANT API REFERENCE:"]
            for ref in tech_refs[:2]:
                matches = ref.get('matches') or []
                parts.append("- %s: %s" % (ref.get('file', ''),
                                           " | ".join(str(m)[:160] for m in matches[:2])))
        if error_report.get('suggested_fix_approach'):
            parts += ["", "SUGGESTED APPROACH: %s" % error_report['suggested_fix_approach']]

        repair_prompt = "\n".join(parts)
        self.history.append({"role": "user", "content": repair_prompt})
        self._append("<br><span style='color:%s'>[REPAIR %d/%d] Feeding the traceback "
                     "and known solutions back to Ollama...</span><br>"
                     % (ACCENT_CYAN, self.repair_attempts, Config.OLLAMA_MAX_REPAIR_ATTEMPTS))
        self._start_generation()

    # -------------------- Phase 10 --------------------

    def context_clicked(self):
        """v3.4.3: show what was actually injected, and why."""
        try:
            # Rebuild against the current prompt box so you can test retrieval
            # WITHOUT spending a generation on it.
            probe = self.prompt.toPlainText().strip()
            if probe:
                self.context_builder.build(probe)
            summary = self.context_builder.describe_last_build()
        except Exception as e:
            summary = "Context inspector failed: %s" % e

        self._append("<br><b><span style='color:%s'>[CONTEXT]</span></b><br>" % ACCENT_CYAN)
        self._append("<pre style='color:#9aa0b0'>%s</pre>" % self._escape(summary))
        App.Console.PrintMessage("\n" + summary + "\n\n")
        self._update_metrics()

    def self_test_clicked(self):
        results = run_ollama_integration_tests(client=self.client)
        self._append("<br><b><span style='color:%s'>[SELF TEST]</span></b><br>" % ACCENT_CYAN)
        for name, passed, detail in results:
            colour = ACCENT_GREEN if passed else CANCEL_RED
            self._append("<span style='color:%s'>[%s] %s — %s</span><br>"
                         % (colour, "PASS" if passed else "FAIL",
                            self._escape(name), self._escape(detail)))

    # -------------------- housekeeping --------------------

    def keyPressEvent(self, event):
        if (event.key() in (Qt.Key_Return, Qt.Key_Enter)
                and (event.modifiers() & Qt.ControlModifier)):
            self.send_clicked()
            return
        super(OllamaChatDialog, self).keyPressEvent(event)

    def closeEvent(self, event):
        global _ollama_generating, _ollama_dialog
        try:
            if hasattr(self, 'heartbeat'):
                self.heartbeat.stop()
            if hasattr(self, 'result_timer'):
                self.result_timer.stop()
            if self.worker is not None and self.worker.isRunning():
                self.worker.cancel()
                self.worker.wait(3000)   # bounded - never block shutdown indefinitely
        except Exception:
            pass
        _ollama_generating = False
        _ollama_dialog = None
        super(OllamaChatDialog, self).closeEvent(event)


def show_ollama_chat():
    """Open the Ollama chat panel (non-modal, single instance)."""
    global _ollama_dialog

    if not Config.OLLAMA_ENABLED:
        App.Console.PrintWarning(
            "[OLLAMA] Disabled - set Config.OLLAMA_ENABLED = True to use it\n")
        return None
    if QtWidgets is None:
        App.Console.PrintError("[OLLAMA] Qt not available - cannot show GUI\n")
        return None

    try:
        if _ollama_dialog is not None:
            _ollama_dialog.raise_()
            _ollama_dialog.activateWindow()
            return _ollama_dialog
        _ollama_dialog = OllamaChatDialog(Gui.getMainWindow())
        _ollama_dialog.show()   # non-modal - FreeCAD stays fully interactive
        return _ollama_dialog
    except Exception as e:
        App.Console.PrintError("[OLLAMA] Error showing chat: %s\n" % e)
        _ollama_dialog = None
        return None


# ============================================================
# PHASE 10 - OLLAMA INTEGRATION TEST SUITE
# ============================================================

def run_ollama_integration_tests(client=None, run_live=False):
    """Category 5 tests. Returns [(name, passed, detail), ...].

    run_live=True adds a real generation round-trip (slow, needs the model
    loaded). Default is the fast structural suite.
    """
    results = []
    client = client or LLMClient()

    # 1. Config sanity
    try:
        ok = (Config.OLLAMA_NUM_CTX >= 8192 and 0 <= Config.OLLAMA_TEMPERATURE <= 1)
        results.append(("Config sanity", ok,
                        "num_ctx=%d temp=%s" % (Config.OLLAMA_NUM_CTX,
                                                Config.OLLAMA_TEMPERATURE)))
    except Exception as e:
        results.append(("Config sanity", False, str(e)))

    # 2. Server reachable
    try:
        up = client.is_server_running()
        results.append(("Ollama server reachable", up,
                        "online" if up else "offline at %s" % client.host))
    except Exception as e:
        results.append(("Ollama server reachable", False, str(e)))

    # 3. Configured model present
    try:
        models = client.list_models()
        present = client.model in models
        results.append(("Configured model installed", present,
                        "%s %s" % (client.model,
                                   "found" if present else "NOT in %d installed" % len(models))))
    except Exception as e:
        results.append(("Configured model installed", False, str(e)))

    # 4. Context builder produces a budgeted prompt
    try:
        built = _ollama_context_builder.build("create a box")
        tokens = _estimate_tokens(built)
        ok = bool(built) and tokens <= Config.OLLAMA_CONTEXT_BUDGET_TOKENS * 1.1
        results.append(("Context builder within budget", ok,
                        "~%d tokens (budget %d)"
                        % (tokens, Config.OLLAMA_CONTEXT_BUDGET_TOKENS)))
    except Exception as e:
        results.append(("Context builder within budget", False, str(e)))

    # 5. Context fits the model window (the silent-truncation guard)
    try:
        tokens = _estimate_tokens(_ollama_context_builder.last_built or "")
        ok = tokens < Config.OLLAMA_NUM_CTX * 0.5
        results.append(("Context fits num_ctx", ok,
                        "~%d tokens vs num_ctx %d" % (tokens, Config.OLLAMA_NUM_CTX)))
    except Exception as e:
        results.append(("Context fits num_ctx", False, str(e)))

    # 6. Code extraction across malformed shapes
    try:
        cases = [
            ("```python\ndoc = App.ActiveDocument\n```", True),
            ("Here you go:\n```\ndoc = App.ActiveDocument\n```\nDone.", True),
            ("<think>hmm</think>\n```python\ndoc = App.ActiveDocument\n```", True),
            ("I cannot help with that.", False),
        ]
        passed = all(bool(extract_python_code(text)[0]) == expected
                     for text, expected in cases)
        results.append(("Code extraction (4 shapes)", passed,
                        "all shapes handled" if passed else "one or more shapes misparsed"))
    except Exception as e:
        results.append(("Code extraction (4 shapes)", False, str(e)))

    # 7. Pre-submission sandbox rejection
    try:
        bad_ok, _ = prevalidate_command("import os\nos.system('dir')")
        good_ok, _ = prevalidate_command("doc = App.ActiveDocument\nimport Part")
        passed = (not bad_ok) and good_ok
        results.append(("Forbidden pattern rejection", passed,
                        "blocked bad / allowed good" if passed else "validation incorrect"))
    except Exception as e:
        results.append(("Forbidden pattern rejection", False, str(e)))

    # 8. Provenance fields present on the learning DB
    try:
        global _learning_system
        if _learning_system:
            patterns = _learning_system.db.get('successful_patterns', [])
            tagged = all('source_agent' in p for p in patterns) if patterns else True
            results.append(("Learning DB provenance tagged", tagged,
                            "%d patterns checked" % len(patterns)))
        else:
            results.append(("Learning DB provenance tagged", False, "learning system not loaded"))
    except Exception as e:
        results.append(("Learning DB provenance tagged", False, str(e)))

    # 9. Bridge input file writable
    try:
        writable = os.access(os.path.dirname(AI_INPUT_FILE), os.W_OK)
        results.append(("Bridge input file writable", writable, AI_INPUT_FILE))
    except Exception as e:
        results.append(("Bridge input file writable", False, str(e)))

    # 10. Registration state
    try:
        registered = _state.is_agent_registered(
            Config.OLLAMA_AGENT_ID, get_bridge_context_hash())
        results.append(("Ollama registered with bridge", registered,
                        "registered" if registered else "not registered (open the chat panel)"))
    except Exception as e:
        results.append(("Ollama registered with bridge", False, str(e)))

    # 11. Optional live round-trip
    if run_live:
        try:
            started = time.time()
            chunks = list(client.stream_chat(
                [{"role": "user", "content": "Reply with exactly: OK"}]))
            text = ''.join(chunks)
            ok = bool(text.strip())
            results.append(("Live generation round-trip", ok,
                            "%.1fs, %d chars" % (time.time() - started, len(text))))
        except Exception as e:
            results.append(("Live generation round-trip", False, str(e)))

    App.Console.PrintMessage("\n" + "=" * 70 + "\n")
    App.Console.PrintMessage("[OLLAMA SELF TEST] %d/%d passed\n"
                             % (sum(1 for r in results if r[1]), len(results)))
    for name, passed, detail in results:
        App.Console.PrintMessage("  [%s] %s - %s\n"
                                 % ("PASS" if passed else "FAIL", name, detail))
    App.Console.PrintMessage("=" * 70 + "\n\n")
    return results


HINT_COLOR = "#c3cad6"      # explanatory text: readable, not shouting
PATH_COLOR = "#aab3c2"      # paths and other incidental detail


def _hint_style(colour=None):
    """The sentence under a control that says what it is for.

    Was a hardcoded mid-grey at ten pixels, written out longhand in ten
    separate places. Ten pixels is about 7.5pt at 96 dpi -- under body
    text and well under the 11pt of the tab labels -- and that grey on
    the #2a2a3d panel is about 3.4:1, below the 4.5:1 that counts as
    readable. Small and dim compound: the operator's word for the
    result was "illegible".

    One name, so the next hint written cannot drift again.
    """
    return "color: %s; font-size: 10pt;" % (colour or HINT_COLOR)


def _path_style():
    """A file path or other detail that must be present but not read
    first. Smaller than a hint, still above the old 10px."""
    return "color: %s; font-size: 9pt;" % PATH_COLOR


def _group_style():
    """A group box whose title clears its own border.

    Qt draws the default title straddling the frame line with no gap, so
    a bold title and a wrapped hint beneath it run together into one
    grey band -- the "poorly presented" half of the complaint.
    """
    return ("QGroupBox { font-size: 10pt; font-weight: bold; color: %s;"
            " border: 1px solid #3a3a4d; border-radius: 6px;"
            " margin-top: 12px; padding: 10px 8px 8px 8px; }"
            "QGroupBox::title { subcontrol-origin: margin;"
            " subcontrol-position: top left; left: 10px;"
            " padding: 0 6px; }" % ACCENT_CYAN)


def _btn_style(colour):
    """One outline button in the Imagineering style, in the given colour.

    v4.0.05: the operator asked for colour-coded buttons. Green to connect,
    cyan to open an editor, blue to check, and amber/red/grey as the
    progressive button escalates -- so the colour carries the meaning
    before the label is read.
    """
    return (
        "QPushButton { background: transparent; color: %s;"
        " border: 1.5px solid %s; border-radius: 6px;"
        " font-weight: bold; padding: 8px 16px; font-size: 10pt; }"
        "QPushButton:hover { background: %s; color: #1e1e2e; }"
        "QPushButton:disabled { color: #555; border-color: #333; }"
        % (colour, colour, colour))


class AIAgentConfigDialog(_BridgeTabsMixin, QtWidgets.QDialog):
    """GUI Dialog for configuring AI Agent I/O settings"""
    
    def __init__(self, parent=None):
        super(AIAgentConfigDialog, self).__init__(parent)
        # v5.0.07: the name and the version, nothing else. The
        # branding is already on the gradient heading inside the window,
        # and a title bar that lists features is not read, it is
        # skipped.
        self.setWindowTitle("AI Bridge v%s" % Config.VERSION)
        self.setMinimumWidth(800)
        self.setMinimumHeight(700)
        # v5.0.07: the window would not resize. Measured on the live
        # dialog: no size grip, no maximize button, and a true floor of
        # 885 against a declared 700 because one tab page demanded 671
        # of height. The pages are in scroll areas now, so the declared
        # minimum is honest; these two give the operator something to
        # actually drag and a button to maximise.
        self.setSizeGripEnabled(True)
        self.setWindowFlags(self.windowFlags()
                            | Qt.WindowMaximizeButtonHint
                            | Qt.WindowMinimizeButtonHint)
        # Imagineering standard palette (Rule 12 theme)
        self.setStyleSheet(
            "QDialog { background: #1e1e2e; color: #e0e0e0; }"
            "QLabel { color: #e0e0e0; }"
            "QGroupBox { color: #00bcd4; border: 1px solid #00bcd4;"
            " border-radius: 6px; margin-top: 10px; padding-top: 8px; }"
            "QGroupBox::title { subcontrol-origin: margin; left: 10px;"
            " padding: 0 4px; }"
            "QPushButton { background: #2a2a3d; color: #e0e0e0;"
            " border: 1.5px solid #00bcd4; border-radius: 6px;"
            " padding: 8px 14px; font-weight: bold; }"
            "QPushButton:hover { background: #00bcd4; color: #1e1e2e; }"
            "QTextEdit { background: #2a2a3d; color: #e0e0e0;"
            " border: 1px solid #3f51b5; border-radius: 4px; }"
            "QComboBox { background: #2a2a3d; color: #e0e0e0;"
            " border: 1.5px solid #00bcd4; border-radius: 4px;"
            " padding: 5px 10px; }"
        )
        
        # Initialize tracking variables for real-time updates
        self._last_output_size = 0
        self._last_input_size = 0
        self._session_cmd_count = 0
        self._session_success_count = 0
        self._session_start_time = datetime.now().isoformat()
        
        self.load_config()
        self.setup_ui()
        self.update_status_timer()
        
        # Run automatic verification
        QtCore.QTimer.singleShot(500, self.run_auto_verification)
    
    def load_config(self):
        """Load configuration"""
        global AI_IO_DIR
        
        if os.path.exists(AI_CONFIG_FILE):
            try:
                with open(AI_CONFIG_FILE, 'r') as f:
                    config = json.load(f)
                    AI_IO_DIR = config.get('io_dir', AI_IO_DIR)
            except Exception as e:
                App.Console.PrintWarning(f"Could not load config file: {e}\n")
                pass
    
    def save_config(self):
        """Save configuration"""
        config = {
            'version': Config.CONFIG_VERSION,
            'io_dir': AI_IO_DIR,
            'learning_dir': LEARNING_DIR,
            'last_updated': datetime.now().isoformat()
        }
        
        try:
            with open(AI_CONFIG_FILE, 'w') as f:
                json.dump(config, f, indent=2)
            return True
        except Exception as e:
            QtWidgets.QMessageBox.warning(self, "Error", f"Could not save config: {str(e)}")
            return False
    
    def setup_ui(self):
        """Setup user interface"""
        # v4.0.01: the Bridge's own controls become the first of four
        # tabs. Only this line and the _assemble_tabs() call at the end
        # of the method changed; every widget between them is as it was.
        self._bridge_page = QtWidgets.QWidget()
        layout = QtWidgets.QVBoxLayout(self._bridge_page)
        
        # Title -- v4.0.07: ONE gradient-painted string rather than a
        # logo widget with a label beside it at another size. The
        # green-cyan-blue now runs across the whole phrase, so the
        # dark blue lands on "AI Bridge" instead of the two halves
        # being different colours at different sizes.
        title_row = QtWidgets.QHBoxLayout()
        title_row.addStretch()
        title_row.addWidget(
            GradientLogoLabel("Imαgineering  -  AI Bridge", 26))
        title_row.addStretch()
        layout.addLayout(title_row)

        # v4.0.02: this was a hardcoded row of [OK]s that could never say
        # anything else -- a display with nothing behind it. The real
        # readiness check already exists in run_auto_verification(); this
        # line is now its one-line summary and moves when it moves.
        self.capability_label = QtWidgets.QLabel("Checking the Bridge...")
        self.capability_label.setAlignment(Qt.AlignCenter)
        self.capability_label.setStyleSheet(
            f"color: {TEXT_COLOR}; font-size: 10pt; padding: 2px;")
        layout.addWidget(self.capability_label)
        
        # ====== BRIDGE STATUS -- one section, not three =================
        # v4.0.02: "LIVE Agent Activity Monitor", "Technique Knowledge" and
        # "System Status" were three boxes. Two of them reported the same
        # thing from two different writers: a 500 ms timer set
        # main_status_label to "Status: [STOPPED]" at fourteen points, while
        # the activity reader set current_op_label to "Idle - Waiting for AI
        # commands" in the box above it. One state, said twice, in two
        # places, at two sizes. Everything below is in ONE group now, and
        # every widget keeps its name so the two updaters are untouched.
        status_group = QtWidgets.QGroupBox("Bridge Status")
        status_group.setStyleSheet(
            "QGroupBox { font-weight: bold; font-size: 11pt; }")
        status_layout = QtWidgets.QVBoxLayout()

        # The one prominent state line.
        self.current_op_label = QtWidgets.QLabel(
            "Idle - waiting for AI commands...")
        self.current_op_label.setStyleSheet(
            "font-size: 12pt; padding: 10px; background-color: #2a2a3d; "
            "border: 2px solid #00bcd4; border-radius: 8px; color: #e0e0e0;"
        )
        status_layout.addWidget(self.current_op_label)

        # v4.0.03: one counters row, and no state word in it. "Stopped"
        # used to sit at the front of this line while the box above said
        # "Idle - waiting for AI commands" -- the same fact, twice, two
        # inches apart. main_status_label is gone; the timer that fed it
        # now feeds the state line through _render_state().
        counters = QtWidgets.QHBoxLayout()
        self.stats_label = QtWidgets.QLabel(
            "0 commands  ·  0 errors  ·  up 0s")
        self.stats_label.setStyleSheet("font-size: 10pt;")
        counters.addWidget(self.stats_label)
        counters.addStretch()
        self.technique_count_label = QtWidgets.QLabel("")
        self.technique_count_label.setStyleSheet(
            "font-size: 10pt; color: #39ff14;")
        counters.addWidget(self.technique_count_label)
        status_layout.addLayout(counters)

        session_row = QtWidgets.QHBoxLayout()
        session_row.addWidget(QtWidgets.QLabel("This session:"))
        self.live_cmd_count = QtWidgets.QLabel("0 commands")
        self.live_success_rate = QtWidgets.QLabel("0% success")
        self.live_last_time = QtWidgets.QLabel("last --:--:--")
        for w in (self.live_cmd_count, self.live_success_rate,
                  self.live_last_time):
            w.setStyleSheet("font-size: 10pt; padding-right: 14px;")
            session_row.addWidget(w)
        session_row.addStretch()
        status_layout.addLayout(session_row)

        # The real-time log. v4.0.02: the technique sentence that used to
        # occupy a group box of its own now goes in the Report View startup
        # text instead, where it is read once rather than sat on screen for
        # the whole session saying the same thing.
        self.agent_log = QtWidgets.QTextEdit()
        self.agent_log.setReadOnly(True)
        self.agent_log.setMaximumHeight(130)
        self.agent_log.setStyleSheet(
            "font-family: 'Consolas', monospace; font-size: 9pt; "
            "background-color: #1e1e2e; color: #39ff14; border: 1px solid #3f51b5;"
        )
        self.agent_log.setPlaceholderText(
            "Commands from your AI will appear here as they run.")
        status_layout.addWidget(self.agent_log)

        # v4.0.03: the readiness report is no longer on screen. It is a
        # diagnostic you run when something looks wrong, not a panel to
        # sit in front of someone for a whole session repeating that the
        # Bridge is stopped. The widget stays -- run_auto_verification()
        # fills it either way -- but it is shown in a dialog, on demand,
        # by the Self-test button.
        self.detail_status = QtWidgets.QTextEdit()
        self.detail_status.setReadOnly(True)
        self.detail_status.setStyleSheet(
            "font-family: 'Consolas', monospace; font-size: 9pt; "
            "background-color: #1e1e2e; color: #e0e0e0; "
            "border: 1px solid #3a3a4d;")

        status_group.setLayout(status_layout)
        # v4.0.05: built here, added AFTER the IDE group below, so the
        # window reads in the order you work: pick an IDE, connect,
        # then watch what happens.

        # v4.0.05: the separate button row is gone. Every button now
        # lives on the IDE line below, which is where the work
        # actually happens.

        # ====== IDE CONNECTION (Multi-IDE Support) ======
        ide_group = QtWidgets.QGroupBox("IDE Connection (AI Bridge)")
        ide_group.setStyleSheet("QGroupBox { font-weight: bold; font-size: 11pt; }")
        ide_layout = QtWidgets.QVBoxLayout()

        ide_desc = QtWidgets.QLabel(
            "Connect FreeCAD AI Bridge to your preferred IDE. The AI assistant in your IDE "
            "can send commands to FreeCAD and receive results via the file-based bridge protocol."
        )
        ide_desc.setWordWrap(True)
        ide_desc.setStyleSheet("color: #e0e0e0; padding: 5px;")
        ide_layout.addWidget(ide_desc)

        # IDE selector row
        ide_select_layout = QtWidgets.QHBoxLayout()

        ide_label = QtWidgets.QLabel("IDE:")
        ide_label.setStyleSheet("font-weight: bold; font-size: 10pt; padding-right: 5px;")
        ide_select_layout.addWidget(ide_label)

        self.ide_combo = QtWidgets.QComboBox()
        self.ide_combo.setStyleSheet("font-size: 10pt; padding: 5px; min-width: 200px;")
        ide_list = IDEManager.get_ide_list_for_display()
        self._ide_keys = []
        for ide_key, display_name in ide_list:
            self.ide_combo.addItem(display_name)
            self._ide_keys.append(ide_key)

        # Set saved preference
        saved_pref = IDEManager.get_saved_preference(AI_CONFIG_FILE)
        if saved_pref in self._ide_keys:
            self.ide_combo.setCurrentIndex(self._ide_keys.index(saved_pref))

        ide_select_layout.addWidget(self.ide_combo)

        # v3.4.1: relabel the launch button per selection - Ollama has no app
        # to launch, so "Open IDE" becomes "Open Chat" for that entry.
        self.ide_combo.currentIndexChanged.connect(self._on_ide_selection_changed)

        # v4.0.03: one button, not two. Connect and Disconnect were a
        # pair in which one was always greyed out -- a state machine
        # drawn on the screen. The label and colour follow the state.
        self.ide_toggle_btn = QtWidgets.QPushButton("Connect")
        self.ide_toggle_btn.clicked.connect(self._ide_toggle_clicked)
        ide_select_layout.addWidget(self.ide_toggle_btn)

        # Kept so _update_ide_connection_state, and update_status_timer's
        # isEnabled() check, keep working. PARENTED AND HIDDEN on purpose:
        # a QPushButton with no parent is a top-level widget, and Qt would
        # draw these two as bare floating windows over FreeCAD.
        self.ide_connect_btn = QtWidgets.QPushButton(
            "Connect", self._bridge_page)
        self.ide_disconnect_btn = QtWidgets.QPushButton(
            "Disconnect", self._bridge_page)
        self.ide_connect_btn.hide()
        self.ide_disconnect_btn.hide()

        # Launch button
        self.ide_launch_btn = QtWidgets.QPushButton("Open IDE")
        self.ide_launch_btn.setStyleSheet(_btn_style("#00bcd4"))
        self.ide_launch_btn.clicked.connect(self.open_ide_with_context)
        ide_select_layout.addWidget(self.ide_launch_btn)

        # v4.0.05: Refresh and Self-test were two buttons doing two
        # halves of one question -- is this set up and working? Check
        # re-detects the IDEs AND runs the self-test, then shows the
        # report.
        self.ide_check_btn = QtWidgets.QPushButton("Check")
        self.ide_check_btn.setToolTip(
            "Re-detect installed IDEs, run the self-test, and show "
            "the readiness report")
        self.ide_check_btn.setStyleSheet(_btn_style("#4a9eff"))
        self.ide_check_btn.clicked.connect(self._check_clicked)
        ide_select_layout.addWidget(self.ide_check_btn)

        # The progressive button. One press pauses, the next
        # disconnects, the next closes -- and the label always names
        # what the NEXT press will do, so it explains itself.
        self.ide_stop_btn = QtWidgets.QPushButton("Close")
        self.ide_stop_btn.clicked.connect(self._stop_step_clicked)
        ide_select_layout.addWidget(self.ide_stop_btn)

        ide_layout.addLayout(ide_select_layout)

        # IDE connection status label
        self.ide_status_label = QtWidgets.QLabel("")
        self.ide_status_label.setStyleSheet("padding: 5px; font-size: 9pt;")
        self._update_ide_connection_state()
        ide_layout.addWidget(self.ide_status_label)

        ide_group.setLayout(ide_layout)
        # v3.4.1: set the launch button label to match the initial selection
        self._on_ide_selection_changed()
        layout.addWidget(ide_group)
        layout.addWidget(status_group)

        # v4.0.01: the Bridge page is built. Put it in the tab set with
        # Project Log, Add IDE and Visual Capture, and give all four one
        # Support & Donation block beneath them. _assemble_tabs() adds that,
        # so it is not added to this page.
        self._assemble_tabs(first=(self._bridge_page, "Bridge"))
        
        # Fast auto-update timer (500ms for real-time feel)
        self.timer = QtCore.QTimer()
        self.timer.timeout.connect(self.update_status_timer)
        self.timer.start(500)  # Update every 500ms for real-time activity
        
        # Track last known file size for efficient updates
        # Start from CURRENT file size so we don't show stale entries from previous sessions
        output_file = os.path.join(AI_IO_DIR, 'ai_output_results.jsonl')
        self._last_output_size = os.path.getsize(output_file) if os.path.exists(output_file) else 0
        self._last_input_size = 0
        self._session_cmd_count = 0
        self._session_success_count = 0
        self._session_start_time = datetime.now().isoformat()
        
        # Update technique count
        self.update_technique_count()
    
    def update_status_timer(self):
        """Update status display"""
        # v5.0.15: the notice's backup line rides this timer. It is the
        # only one that already ticks on this dialog, and without it the
        # reminder never updated at all.
        try:
            self._refresh_fork()
        except BaseException:
            pass
        try:
            stats = _state.get_stats()
            
            # Update main status
            if stats['monitoring_active']:
                if stats['error_rate'] > 0.5:
                    self._state_word = "Degraded - errors on most commands"
                    self._state_colour = "#ffb300"
                else:
                    if _paused:
                        self._state_word = ("Paused - connected, but taking "
                                            "no new commands")
                        self._state_colour = "#ffb300"
                    else:
                        self._state_word = ("Connected - listening for "
                                            "commands")
                        self._state_colour = ACCENT_GREEN
            else:
                self._state_word = ("Not connected - choose an IDE below and press Connect")
                self._state_colour = "#888888"
            
            self._render_state()

            # Update stats
            self.stats_label.setText(
                f"{stats['commands_processed']} commands  \u00b7  "
                f"{stats['errors_count']} errors  \u00b7  "
                f"up {int(stats['uptime_seconds'])}s"
            )
            
            # Update agent activity
            self.update_agent_activity()

            # Keep IDE connection buttons in sync with monitoring state
            if hasattr(self, 'ide_connect_btn'):
                connected = stats['monitoring_active']
                if self.ide_connect_btn.isEnabled() == connected:
                    self._update_ide_connection_state()
            
        except Exception:
            # Silently ignore errors in status update to prevent loops
            pass
    
    def update_agent_activity(self):
        """Update the agent activity display with real-time command monitoring"""
        try:
            # Check INPUT file for pending commands (shows what AI is sending)
            input_file = os.path.join(AI_IO_DIR, 'ai_input_commands.jsonl')
            output_file = os.path.join(AI_IO_DIR, 'ai_output_results.jsonl')
            
            # Check for new input commands (pending)
            input_size = 0
            pending_cmd = None
            if os.path.exists(input_file):
                input_size = os.path.getsize(input_file)
                if input_size > self._last_input_size:
                    # New command incoming!
                    self._last_input_size = input_size
                    try:
                        with open(input_file, 'r', encoding='utf-8') as f:
                            lines = f.readlines()
                        if lines:
                            last_line = lines[-1].strip()
                            if last_line:
                                data = json.loads(last_line)
                                pending_cmd = data.get('description', data.get('command', '')[:50])
                    except:
                        pass
            
            if pending_cmd:
                self._op_text = f"running {pending_cmd}"
                self._render_state()
                self.current_op_label.setStyleSheet(
                    "font-size: 12pt; padding: 10px; background-color: #2a1a00; "
                    "border: 2px solid #ff9900; border-radius: 8px; color: #ffcc00;"
                )
            
            # Check OUTPUT file for results
            if not os.path.exists(output_file):
                return
            
            output_size = os.path.getsize(output_file)
            if output_size == self._last_output_size:
                return  # No new data
            
            self._last_output_size = output_size
            
            # Read last entries
            with open(output_file, 'r', encoding='utf-8') as f:
                lines = f.readlines()
            
            if not lines:
                return
            
            # Parse recent commands for the log
            recent_entries = []
            for line in lines[-10:]:
                try:
                    data = json.loads(line.strip())
                    if 'content' in data and isinstance(data['content'], dict):
                        content = data['content']
                        cmd_id = content.get('command_id', 'unknown')[:15]
                        success = content.get('success', False)
                        error_type = content.get('error_details', {}).get('error_type', '') if not success else ''
                        preview = content.get('command_preview', content.get('original_command', ''))[:40]
                        timestamp = content.get('timestamp', '')
                        
                        # Track session stats
                        self._session_cmd_count += 1
                        if success:
                            self._session_success_count += 1
                        
                        # Format time
                        time_str = '??:??:??'
                        if timestamp:
                            try:
                                dt = datetime.fromisoformat(timestamp.replace('Z', '+00:00'))
                                time_str = dt.strftime('%H:%M:%S')
                            except:
                                pass
                        
                        status_icon = '✅' if success else '❌'
                        if success:
                            entry = f"[{time_str}] {status_icon} {cmd_id}: {preview}"
                        else:
                            entry = f"[{time_str}] {status_icon} {cmd_id}: {error_type} - {preview}"
                        recent_entries.append(entry)
                except:
                    continue
            
            if recent_entries:
                # Update the current operation label with most recent result
                last = recent_entries[-1]
                if '✅' in last:
                    self._op_text = f"done: {last[13:]}"
                    self._render_state()
                    self.current_op_label.setStyleSheet(
                        "font-size: 12pt; padding: 10px; background-color: #1a2e1a; "
                        "border: 2px solid #28a745; border-radius: 8px; color: #00ff00;"
                    )
                else:
                    self._op_text = f"error: {last[13:]}"
                    self._render_state()
                    self.current_op_label.setStyleSheet(
                        "font-size: 12pt; padding: 10px; background-color: #2e1a1a; "
                        "border: 2px solid #dc3545; border-radius: 8px; color: #ff4444;"
                    )
                
                # Update the log (newest at top)
                log_text = '\n'.join(reversed(recent_entries[-8:]))
                self.agent_log.setPlainText(log_text)
                
                # Auto-scroll to top (newest)
                cursor = self.agent_log.textCursor()
                cursor.movePosition(cursor.Start)
                self.agent_log.setTextCursor(cursor)
                
                # Update live stats
                self.live_cmd_count.setText(f"Session: {self._session_cmd_count} commands")
                if self._session_cmd_count > 0:
                    rate = (self._session_success_count / self._session_cmd_count) * 100
                    self.live_success_rate.setText(f"Success: {rate:.0f}%")
                
                self.live_last_time.setText(f"Last: {time_str}")
                
        except Exception as e:
            pass  # Silently ignore to prevent error loops
    
    def quick_capture_clicked(self):
        """Quick capture the last successful command with minimal input"""
        try:
            output_file = os.path.join(AI_IO_DIR, 'ai_output_results.jsonl')
            if not os.path.exists(output_file):
                QtWidgets.QMessageBox.warning(self, "No Data", "No command history found.")
                return
            
            with open(output_file, 'r', encoding='utf-8') as f:
                lines = f.readlines()
            
            # Find last successful command
            last_success = None
            for line in reversed(lines):
                try:
                    data = json.loads(line.strip())
                    if 'content' in data and isinstance(data['content'], dict):
                        content = data['content']
                        if content.get('success', False):
                            last_success = content
                            break
                except:
                    continue
            
            if not last_success:
                QtWidgets.QMessageBox.warning(self, "No Success", "No successful commands found to capture.")
                return
            
            # Quick capture dialog
            dialog = QuickCaptureDialog(last_success, self)
            if dialog.exec_() == QtWidgets.QDialog.Accepted:
                self.update_technique_count()
                
        except Exception as e:
            QtWidgets.QMessageBox.warning(self, "Error", f"Could not capture:\n{str(e)}")
    
    def update_technique_count(self):
        """Update the technique count from community knowledge"""
        try:
            index_file = os.path.join(
                library_dir(), 'Community_Knowledge',
                'Techniques_Index.json')
            if os.path.exists(index_file):
                with open(index_file, 'r', encoding='utf-8') as f:
                    data = json.load(f)
                total = data.get('metadata', {}).get('total_techniques', 0)
                verified = data.get('metadata', {}).get('verified_count', 0)
                self.technique_count_label.setText(
                    f"{verified} of {total} techniques verified")
            else:
                self.technique_count_label.setText("")
        except Exception:
            self.technique_count_label.setText("")
    
    def capture_technique_clicked(self):
        """Capture the last successful technique for community knowledge"""
        try:
            # Read last successful command from output
            output_file = os.path.join(AI_IO_DIR, 'ai_output_results.jsonl')
            if not os.path.exists(output_file):
                QtWidgets.QMessageBox.warning(self, "No Data", "No command history found.")
                return
            
            with open(output_file, 'r', encoding='utf-8') as f:
                lines = f.readlines()
            
            # Find last successful command
            last_success = None
            for line in reversed(lines):
                try:
                    data = json.loads(line.strip())
                    if 'content' in data and isinstance(data['content'], dict):
                        content = data['content']
                        if content.get('success', False):
                            last_success = content
                            break
                except:
                    continue
            
            if not last_success:
                QtWidgets.QMessageBox.warning(self, "No Success", "No successful commands found to capture.")
                return
            
            # Show capture dialog
            dialog = TechniqueCaptureDialog(last_success, self)
            if dialog.exec_() == QtWidgets.QDialog.Accepted:
                self.update_technique_count()
                QtWidgets.QMessageBox.information(
                    self, "Captured!", 
                    f"Technique saved to Community_Knowledge/Submissions/\n\n"
                    f"It will be verified and promoted to the main knowledge base."
                )
        except Exception as e:
            QtWidgets.QMessageBox.warning(self, "Error", f"Could not capture technique:\n{str(e)}")
    
    def _set_capability_line(self, monitoring, io_ok, health_ok, patterns):
        """The one-line summary under the title. v4.0.02: this used to be
        three hardcoded [OK]s that never changed; now it says what the
        readiness check below actually found."""
        try:
            bits = [
                "Security: sandboxed, paths checked",
                "Reliability: %s" % ("auto-recovery, health reporting"
                                     if health_ok else
                                     "auto-recovery (health file pending)"),
                "Learning: %s" % ("%d entries" % patterns if patterns
                                  else "nothing captured yet"),
            ]
            # v4.0.03: no connection state here. It is the one fact the
            # window used to state five times; it now lives in the status
            # line alone. This row is about what the Bridge CAN do, which
            # does not change when you connect.
            colour = ACCENT_GREEN if io_ok else "#ffb300"
            self.capability_label.setText("  |  ".join(bits))
            self.capability_label.setStyleSheet(
                "color: %s; font-size: 10pt; padding: 2px;" % colour)
        except BaseException:
            pass

    def run_auto_verification(self):
        """Run connection verification"""
        results = []
        all_ok = True
        
        results.append("[Production Readiness Check]...\n" + "="*60 + "\n")
        
        # Check monitoring
        results.append("[1/7] Monitoring Status...")
        if _state.monitoring_active:
            results.append("[OK] ACTIVE\n")
        else:
            results.append("[STOPPED]\n")
        
        # Check directories
        results.append("[2/7] Directory Structure...")
        if os.path.exists(AI_IO_DIR):
            results.append(f"[OK] {AI_IO_DIR}\n")
        else:
            results.append(f"[ERROR] Missing\n")
            all_ok = False
        
        # Check security
        results.append("[3/7] Security Systems...")
        results.append("[OK] Command sandboxing active\n")
        results.append("[OK] Path validation enabled\n")
        
        # Check reliability
        results.append("[4/7] Reliability Features...")
        results.append("[OK] Crash recovery active\n")
        results.append("[OK] Auto-flush enabled\n")
        
        # Check files
        results.append("[5/7] I/O Files...")
        if os.path.exists(AI_INPUT_FILE):
            size = os.path.getsize(AI_INPUT_FILE)
            results.append(f"[OK] Input: {size} bytes\n")
        else:
            results.append("[ERROR] Input file missing\n")
            all_ok = False
        
        # Check health
        results.append("[6/7] Health Check...")
        if os.path.exists(HEALTH_CHECK_FILE):
            results.append("[OK] Health monitoring active\n")
        else:
            results.append("[WARN] Health file not created yet\n")
        
        # Check learning
        results.append("[7/7] Learning System...")
        try:
            stats = _learning_system.get_stats()
            results.append(f"[OK] {stats['total_patterns']} patterns learned\n")
        except Exception as e:
            results.append(f"[WARN] Learning system error: {e}\n")
        
        results.append("\n" + "="*60 + "\n")
        if all_ok and _state.monitoring_active:
            results.append("[OK] SYSTEM READY FOR PRODUCTION USE")
        elif _state.monitoring_active:
            results.append("[WARN] SYSTEM ACTIVE - Minor Issues Detected")
        else:
            results.append("[STOPPED] NOT CONNECTED - press Connect below")
        results.append("\n" + "="*60)
        
        self.detail_status.setPlainText('\n'.join(results))

        # v4.0.02: feed the one-line summary under the title from what
        # was just measured, rather than leaving it to say whatever it
        # was built with.
        try:
            _pat = 0
            try:
                _pat = _learning_system.get_stats().get(
                    'total_patterns', 0)
            except BaseException:
                pass
            self._set_capability_line(
                _state.monitoring_active,
                os.path.exists(AI_IO_DIR)
                and os.path.exists(AI_INPUT_FILE),
                os.path.exists(HEALTH_CHECK_FILE),
                _pat)
        except BaseException:
            pass
    
    def start_monitoring_clicked(self):
        """Start monitoring button handler"""
        if start_ai_monitoring():
            QtWidgets.QMessageBox.information(self, "Success", "Monitoring started successfully!")
            self.run_auto_verification()
        else:
            QtWidgets.QMessageBox.warning(self, "Error", "Failed to start monitoring")
    
    def stop_monitoring_clicked(self):
        """Stop monitoring button handler"""
        if stop_ai_monitoring():
            QtWidgets.QMessageBox.information(self, "Success", "Monitoring stopped")
            self.run_auto_verification()
        else:
            QtWidgets.QMessageBox.warning(self, "Error", "Monitoring was not active")
    
    def run_tests_clicked(self):
        """Self-test, then show the readiness report in a window of its own.

        v4.0.03: the report used to occupy a pane on the main window for the
        whole session. It is a thing you go and look at, so it opens when
        you ask for it and closes when you are done.
        """
        run_comprehensive_self_test()
        self.run_auto_verification()
        try:
            dlg = QtWidgets.QDialog(self)
            dlg.setWindowTitle("Self-test and readiness")
            dlg.setMinimumSize(620, 460)
            lay = QtWidgets.QVBoxLayout(dlg)
            view = QtWidgets.QTextEdit()
            view.setReadOnly(True)
            view.setStyleSheet(
                "font-family: 'Consolas', monospace; font-size: 9pt; "
                "background-color: #1e1e2e; color: #e0e0e0;")
            view.setPlainText(self.detail_status.toPlainText())
            lay.addWidget(view)
            close = QtWidgets.QPushButton("Close")
            close.clicked.connect(dlg.accept)
            row = QtWidgets.QHBoxLayout()
            row.addStretch()
            row.addWidget(close)
            lay.addLayout(row)
            dlg.show()          # Rule 14: never exec() a dialog in FreeCAD
            self._readiness_dlg = dlg
        except BaseException as exc:
            App.Console.PrintWarning(
                "[BRIDGE] Could not show the readiness report: %s\n" % exc)
    
    def connect_ide_clicked(self):
        """Connect button handler - starts monitoring for the selected IDE"""
        idx = self.ide_combo.currentIndex()
        ide_key = self._ide_keys[idx] if idx >= 0 and idx < len(self._ide_keys) else 'vscode'
        # v4.0.02: all_ides(), not the fixed table -- an editor the
        # operator added in the Add IDE tab is not in SUPPORTED_IDES, so
        # this showed its raw key ("custom:sublime text") as the name.
        _every = IDEManager.all_ides()
        ide_name = _every.get(ide_key, {}).get('name', ide_key)
        ai_name = _every.get(ide_key, {}).get('ai_name', 'AI')

        # Save preference
        IDEManager.save_preference(AI_CONFIG_FILE, ide_key)

        # Generate context file
        try:
            IDEManager.generate_context_file(ide_key, AI_IO_DIR, LEARNING_DIR)
            IDEManager.sync_workspace_bridge_files(AI_IO_DIR)
        except Exception:
            pass

        # v4.0.05: a pause from a previous session must not carry over
        # into a fresh connection and silently swallow every command.
        global _paused
        _paused = False

        # Start monitoring
        if start_ai_monitoring():
            # Reset LIVE monitor to clean state for this session
            output_file = os.path.join(AI_IO_DIR, 'ai_output_results.jsonl')
            self._last_output_size = os.path.getsize(output_file) if os.path.exists(output_file) else 0
            self._session_cmd_count = 0
            self._session_success_count = 0
            self._session_start_time = datetime.now().isoformat()
            self.current_op_label.setText("Idle - Waiting for AI commands...")
            self.current_op_label.setStyleSheet(
                "font-size: 12pt; padding: 10px; background-color: #1a1a2e; "
                "border: 2px solid #4a9eff; border-radius: 8px; color: #ffffff;"
            )
            self.agent_log.clear()
            self.live_cmd_count.setText("Session: 0 commands")
            self.live_success_rate.setText("Success: 0%")
            self.live_last_time.setText("Last: --:--:--")

            App.Console.PrintMessage(f"\n[CONNECTED] Bridge active for {ide_name}\n")
            App.Console.PrintMessage(f"[OK] Monitoring started - {ai_name} can now send commands to FreeCAD\n\n")

            # Print AI startup instructions now that we're connected
            App.Console.PrintMessage("="*70 + "\n")
            App.Console.PrintMessage(f"[AI BRIDGE CONNECTED TO {ide_name.upper()}]\n")
            App.Console.PrintMessage("="*70 + "\n")
            App.Console.PrintMessage(f"AI assistants: send commands via {AI_INPUT_FILE}\n")
            App.Console.PrintMessage(f"Read results from {AI_OUTPUT_FILE}\n\n")

            # Check for active document — warn AI agents if none exists
            if App.ActiveDocument is None:
                App.Console.PrintWarning("\n[WARNING] No active document! AI agents must create one first:\n")
                App.Console.PrintWarning("  App.newDocument('ProjectName')\n\n")
            else:
                App.Console.PrintMessage(f"[OK] Active document: {App.ActiveDocument.Name}\n")

            # CRITICAL PYTHON RULES - embedded in Report View so copy-paste delivers them
            App.Console.PrintMessage("="*70 + "\n")
            App.Console.PrintMessage("[CRITICAL PYTHON RULES FOR AI ASSISTANTS]\n")
            App.Console.PrintMessage("="*70 + "\n")
            App.Console.PrintMessage("RULE 1: Each command runs in a FRESH exec() scope.\n")
            App.Console.PrintMessage("  Variables DO NOT persist between commands.\n")
            App.Console.PrintMessage("  EVERY command MUST start with: doc = App.ActiveDocument\n")
            App.Console.PrintMessage("  EVERY command MUST include its own imports: import Part; import math\n")
            App.Console.PrintMessage("RULE 2: For loops/if blocks need REAL newlines (\\n), not semicolons.\n")
            App.Console.PrintMessage("  WRONG: for i in range(5): obj = Part.makeSphere(5); ...\n")
            App.Console.PrintMessage("  RIGHT: Use \\n with indentation in the JSONL code field.\n")
            App.Console.PrintMessage("RULE 3: No backslashes inside f-string {expressions}.\n")
            App.Console.PrintMessage("RULE 4: import os/sys/subprocess are BLOCKED by security sandbox.\n")
            App.Console.PrintMessage("RULE 5: Always call App.ActiveDocument.recompute() after geometry changes.\n")
            App.Console.PrintMessage("RULE 6: Prefer ONE big command with all objects over many small ones.\n")
            App.Console.PrintMessage("RULE 7: Read AI_Bridge_Python_Rules.txt and ai_context_summary.txt FIRST.\n")
            App.Console.PrintMessage("  Python Rules: " + (library_file("AI_Bridge_Python_Rules.txt")
                 or os.path.join(library_dir(),
                                 "AI_Bridge_Python_Rules.txt")) + "\n")
            App.Console.PrintMessage("  Context Summary: " + os.path.join(AI_IO_DIR, "ai_context_summary.txt") + "\n")
            App.Console.PrintMessage("="*70 + "\n\n")

            self._update_ide_connection_state()
            self.run_auto_verification()
        else:
            if _state.monitoring_active:
                App.Console.PrintMessage(f"[CONNECTED] Already connected\n")
                self._update_ide_connection_state()
            else:
                QtWidgets.QMessageBox.warning(self, "Error", "Failed to start monitoring")

    def disconnect_ide_clicked(self):
        """Disconnect button handler - stops monitoring"""
        if stop_ai_monitoring():
            App.Console.PrintMessage("\n[DISCONNECTED] Bridge monitoring stopped\n")
            self._update_ide_connection_state()
            self.run_auto_verification()
        else:
            QtWidgets.QMessageBox.warning(self, "Error", "Monitoring was not active")
            self._update_ide_connection_state()

    def _render_state(self):
        """The one state line, composed from both writers.

        Until 4.0.03 update_status_timer owned main_status_label and
        update_agent_activity owned current_op_label: two widgets, two
        sizes, the same fact. Both now set a field and call this.
        """
        try:
            word = getattr(self, "_state_word", "Checking...")
            colour = getattr(self, "_state_colour", "#888888")
            op = getattr(self, "_op_text", "")
            self.current_op_label.setText(
                word if not op else "%s  -  %s" % (word, op))
            self.current_op_label.setStyleSheet(
                "font-size: 12pt; padding: 10px; background-color: #2a2a3d; "
                "border: 2px solid %s; border-radius: 8px; color: %s;"
                % (colour, colour))
        except BaseException:
            pass

    def _ide_toggle_clicked(self):
        """The run button: connect, then pause and resume.

        v4.0.06. This used to be Connect/Disconnect, which meant two
        buttons on the row could disconnect -- this one, and press two
        of the wind-down button beside it. Disconnecting now belongs
        to that one alone, and this button owns what the Bridge is
        DOING: not connected, listening, or paused.
        """
        global _paused
        if not _state.monitoring_active:
            self.connect_ide_clicked()
        elif _paused:
            _paused = False
            App.Console.PrintMessage(
                "\n[BRIDGE] Resumed. Listening for commands again.\n")
        else:
            _paused = True
            App.Console.PrintMessage(
                "\n[BRIDGE] Paused. Still connected, but taking no new "
                "commands. Press Resume to carry on.\n")
        self._update_ide_connection_state()

    def _sync_toggle(self, connected, ide_name=""):
        """Label and colour the run button for the state it is in."""
        try:
            if not connected:
                self.ide_toggle_btn.setText("Connect")
                self.ide_toggle_btn.setToolTip(
                    "Start the Bridge for the selected IDE")
                self.ide_toggle_btn.setStyleSheet(_btn_style("#39ff14"))
            elif _paused:
                self.ide_toggle_btn.setText("Resume")
                self.ide_toggle_btn.setToolTip(
                    "Paused. Start taking commands again.")
                self.ide_toggle_btn.setStyleSheet(_btn_style("#39ff14"))
            else:
                self.ide_toggle_btn.setText("Pause")
                self.ide_toggle_btn.setToolTip(
                    "Stop taking new commands. Stays connected, and "
                    "anything already running finishes.")
                self.ide_toggle_btn.setStyleSheet(_btn_style("#ffb300"))
        except BaseException:
            pass

    def _check_clicked(self):
        """Re-detect the IDEs and run the self-test, in one press."""
        try:
            self.refresh_ide_detection()
        except BaseException as exc:
            App.Console.PrintWarning(
                "[BRIDGE] IDE re-detection failed: %s\n" % exc)
        self.run_tests_clicked()

    def _stop_step_clicked(self):
        """The wind-down button: disconnect, then close.

        v4.0.06. The operator asked for one button that steps down, and
        this is it -- press once to disconnect, again to close. Pause
        used to be its first press, which made a pause impossible to
        undo: the only way on was to disconnect. Pause now lives on the
        run button beside this one, where it has a Resume.

        The press that was asked for and is NOT here is "stop the
        current operation". It cannot exist: commands run SYNCHRONOUSLY
        on the GUI thread, so while one runs this window cannot receive
        the click at all, and killing it part-way would corrupt the
        document. Pausing is the honest version -- no new commands are
        taken, and whatever is running finishes.
        """
        global _paused
        if _state.monitoring_active:
            _paused = False
            self.disconnect_ide_clicked()
        else:
            self.close()
        self._sync_stop_step()

    def _sync_stop_step(self):
        """Label and colour the wind-down button for its next press."""
        try:
            if _state.monitoring_active:
                self.ide_stop_btn.setText("Disconnect")
                self.ide_stop_btn.setToolTip(
                    "Stop the Bridge. Press again to close the window.")
                self.ide_stop_btn.setStyleSheet(_btn_style("#F4424D"))
            else:
                self.ide_stop_btn.setText("Close")
                self.ide_stop_btn.setToolTip(
                    "Not connected. Close this window.")
                self.ide_stop_btn.setStyleSheet(_btn_style("#9e9e9e"))
        except BaseException:
            pass

    def _update_ide_connection_state(self):
        """Update Connect/Disconnect buttons and status label based on monitoring state"""
        if _state.monitoring_active:
            # Connected state -- v4.0.06: which may be paused, and the
            # status line has to say so or the operator sees a connected
            # Bridge quietly ignoring every command.
            idx = self.ide_combo.currentIndex()
            ide_key = self._ide_keys[idx] if idx >= 0 and idx < len(self._ide_keys) else 'vscode'
            ide_name = IDEManager.all_ides().get(ide_key, {}).get(
                'name', ide_key)
            self._sync_toggle(True, ide_name)
            self._sync_stop_step()
            if _paused:
                self.ide_status_label.setText(
                    f"PAUSED - connected to {ide_name}, but taking no "
                    f"commands. Press Resume.")
            else:
                self.ide_status_label.setText(f"Connected to {ide_name} - Bridge monitoring active")
            self.ide_status_label.setStyleSheet("padding: 5px; font-size: 9pt; color: #4caf50; font-weight: bold;")
            self.ide_connect_btn.setEnabled(False)
            self.ide_disconnect_btn.setEnabled(True)
            self.ide_combo.setEnabled(False)
        else:
            # Disconnected state
            self._sync_toggle(False)
            self._sync_stop_step()
            detected = IDEManager.detect_installed_ides()
            names = [info['name'] for info in detected.values()]
            if names:
                self.ide_status_label.setText(f"Disconnected - Select IDE and click Connect ({', '.join(names)} detected)")
                self.ide_status_label.setStyleSheet("padding: 5px; font-size: 9pt; color: #ff9800;")
            else:
                self.ide_status_label.setText("Disconnected - No supported IDEs detected")
                self.ide_status_label.setStyleSheet("padding: 5px; font-size: 9pt; color: #f44336;")
            self.ide_connect_btn.setEnabled(True)
            self.ide_disconnect_btn.setEnabled(False)
            self.ide_combo.setEnabled(True)

    def _on_ide_selection_changed(self, index=None):
        """v3.4.1: adapt the launch button to the selected target.

        Ollama is an inference server, not an editor - there is no application
        to open, so the button opens the local chat panel instead and says so.
        """
        try:
            if not hasattr(self, '_ide_keys') or not self._ide_keys:
                return
            idx = self.ide_combo.currentIndex()
            if idx < 0 or idx >= len(self._ide_keys):
                return
            ide_key = self._ide_keys[idx]
            is_local = IDEManager.SUPPORTED_IDES.get(ide_key, {}).get('is_local_chat', False)

            if is_local:
                self.ide_launch_btn.setText("Open Chat")
                self.ide_launch_btn.setToolTip(
                    "Open the local Ollama chat panel. The model talks to FreeCAD "
                    "through this same bridge, with the same sandbox.")
            else:
                self.ide_launch_btn.setText("Open IDE")
                self.ide_launch_btn.setToolTip(
                    "Launch the selected IDE with the AI Bridge Workspace loaded.")
        except Exception as e:
            App.Console.PrintWarning(f"[IDE] Selection change: {e}\n")

    def update_ide_status_label(self):
        """Update the IDE detection status display (legacy - now delegates to connection state)"""
        self._update_ide_connection_state()

    def refresh_ide_detection(self):
        """Re-detect installed IDEs and update dropdown"""
        IDEManager.refresh_detection()
        ide_list = IDEManager.get_ide_list_for_display()
        current_key = self._ide_keys[self.ide_combo.currentIndex()] if self._ide_keys else 'vscode'

        self.ide_combo.clear()
        self._ide_keys = []
        for ide_key, display_name in ide_list:
            self.ide_combo.addItem(display_name)
            self._ide_keys.append(ide_key)

        if current_key in self._ide_keys:
            self.ide_combo.setCurrentIndex(self._ide_keys.index(current_key))

        self.update_ide_status_label()
        App.Console.PrintMessage("[IDE] Re-detected installed IDEs\n")

    def open_ide_with_context(self):
        """Open the selected IDE with the AI Bridge Workspace folder.
        The workspace contains rules files and helper tools that
        automatically instruct the AI how to talk to FreeCAD.
        """
        try:
            idx = self.ide_combo.currentIndex()
            ide_key = self._ide_keys[idx] if idx >= 0 and idx < len(self._ide_keys) else 'vscode'
            ide_name = IDEManager.SUPPORTED_IDES.get(ide_key, {}).get('name', ide_key)
            ai_name = IDEManager.SUPPORTED_IDES.get(ide_key, {}).get('ai_name', 'AI')

            # Save preference
            IDEManager.save_preference(AI_CONFIG_FILE, ide_key)

            # v3.4.2: the local-chat path is NOT an editor launch. Writing an
            # IDE instruction file and reporting a workspace open for Ollama is
            # actively misleading - Ollama is a headless inference server with
            # no editor, no workspace and no filesystem access, so it can never
            # read a rules file. Its knowledge arrives by direct injection into
            # the system prompt on every message instead (OllamaContextBuilder).
            is_local_chat = IDEManager.SUPPORTED_IDES.get(ide_key, {}).get('is_local_chat', False)

            if is_local_chat:
                success, message = IDEManager.launch_ide(ide_key)
                if not success:
                    App.Console.PrintError(f"[OLLAMA] {message}\n")
                    QtWidgets.QMessageBox.warning(self, "Ollama Chat", message)
                    return

                try:
                    ctx_tokens = _ollama_context_builder.last_tokens
                except Exception:
                    ctx_tokens = 0

                App.Console.PrintMessage("\n" + "=" * 70 + "\n")
                App.Console.PrintMessage("[OLLAMA] Local AI chat panel opened\n")
                App.Console.PrintMessage("=" * 70 + "\n")
                App.Console.PrintMessage(
                    "No editor and no workspace are involved. Knowledge is injected\n"
                    "directly into the model's system prompt on every message.\n")
                App.Console.PrintMessage(f"Model: {Config.OLLAMA_MODEL}   "
                                         f"num_ctx: {Config.OLLAMA_NUM_CTX}\n")
                App.Console.PrintMessage(f"Context injected: ~{ctx_tokens} tokens "
                                         f"(budget {Config.OLLAMA_CONTEXT_BUDGET_TOKENS})\n\n")

                QtWidgets.QMessageBox.information(
                    self,
                    "Ollama - Local AI Chat",
                    "The local AI chat panel is open.\n\n"
                    "There is NO editor and NO workspace in this path — Ollama is a "
                    "headless server, so it cannot read .windsurfrules or any other "
                    "rules file.\n\n"
                    "Instead, every message you send carries an injected system prompt "
                    "containing:\n"
                    "  • Core execution rules (fresh exec scope, mandatory doc = "
                    "App.ActiveDocument, allowed/blocked modules)\n"
                    "  • Knowledge-base patterns retrieved for your prompt\n"
                    "  • VERIFIED successful commands from the learning database\n"
                    "  • Live document state (objects and current selection)\n\n"
                    f"Injected this session: ~{ctx_tokens} tokens of a "
                    f"{Config.OLLAMA_CONTEXT_BUDGET_TOKENS} budget.\n\n"
                    "Unlike Claude Code, the model cannot browse files on demand — it "
                    "only sees this curated slice. Unverified patterns are withheld by "
                    "the provenance gate.\n\n"
                    "Generated code appears in the review pane; press Send to Bridge to "
                    "execute it."
                )
                return

            # ---- editor path (unchanged) ----
            # Generate/update bridge instructions, then sync the workspace assets AI clients use.
            IDEManager.generate_context_file(ide_key, AI_IO_DIR, LEARNING_DIR)
            IDEManager.sync_workspace_bridge_files(AI_IO_DIR)

            # Launch IDE with the workspace FOLDER (this triggers rules file reading)
            success, message = IDEManager.launch_ide(ide_key)

            if success:
                App.Console.PrintMessage("\n" + "="*70 + "\n")
                App.Console.PrintMessage(f"[{ide_name}] Opened AI Bridge Workspace\n")
                App.Console.PrintMessage("="*70 + "\n")
                App.Console.PrintMessage(f"The AI ({ai_name}) will automatically read the rules file\n")
                App.Console.PrintMessage("and know how to send commands to FreeCAD.\n")
                App.Console.PrintMessage(f"Workspace: {IDEManager.WORKSPACE_DIR}\n\n")
                App.Console.PrintMessage("The AI can run: python send_to_freecad.py \"command\"\n")
                App.Console.PrintMessage("to execute any FreeCAD Python command.\n\n")

                # IDE-specific rules file info
                # v3.4.2: 'devin' replaces the retired 'windsurf' key, and the
                # fallback no longer silently claims '.windsurfrules' for
                # anything unlisted - that default is exactly what produced a
                # wrong instruction dialog for a non-editor target.
                rules_map = {
                    'devin': '.devin/ (legacy .windsurfrules still honoured)',
                    'cursor': '.cursorrules',
                    'vscode': '.continuerules or .github/copilot-instructions.md',
                    'zed': 'CLAUDE.md',
                    'claude-code': 'CLAUDE.md',
                }
                rules_file = rules_map.get(ide_key, 'the workspace rules file (if this editor supports one)')

                QtWidgets.QMessageBox.information(
                    self,
                    f"{ide_name} - AI Bridge Connected",
                    f"{ide_name} opened with AI Bridge Workspace.\n\n"
                    f"The {ai_name} will automatically read:\n"
                    f"  {rules_file}\n\n"
                    f"This gives it full instructions to:\n"
                    f"  Send commands to FreeCAD\n"
                    f"  Read results automatically\n"
                    f"  Access all knowledge bases\n"
                    f"  Self-correct on errors\n\n"
                    f"Just ask the AI to do something in FreeCAD!"
                )
            else:
                App.Console.PrintError(f"[IDE] {message}\n")
                QtWidgets.QMessageBox.warning(
                    self,
                    "IDE Not Found",
                    f"{message}\n\n"
                    "Tip: You can also use the bridge from any terminal:\n"
                    "  python send_to_freecad.py \"App.newDocument('Test')\"\n\n"
                    "Or open the workspace folder manually:\n"
                    f"  {IDEManager.WORKSPACE_DIR}"
                )

        except Exception as e:
            App.Console.PrintError(f"Error opening IDE: {str(e)}\n")
            QtWidgets.QMessageBox.warning(
                self,
                "Error",
                f"Could not open IDE:\n{str(e)}"
            )
    
    def open_ollama_chat_clicked(self):
        """v3.4.0: open the Ollama local-AI chat panel."""
        try:
            show_ollama_chat()
        except Exception as e:
            App.Console.PrintError(f"[OLLAMA] Could not open chat: {e}\n")

    def closeEvent(self, event):
        """Stop the Bridge, then close.

        v4.0.04, on the operator's instruction. Before this, closing
        the window left the monitor timers running with nothing on
        screen to say so -- they are parented to FreeCAD main window,
        not to this dialog, so the dialog going away never touched
        them. Re-running the macro to get the window back then made a
        SECOND Bridge poll the same files beside the first, with the
        first unreachable.
        """
        try:
            if hasattr(self, "timer"):
                self.timer.stop()          # the display refresh
        except BaseException:
            pass
        try:
            if _state.monitoring_active:
                stop_ai_monitoring()
                App.Console.PrintMessage(
                    "\n[BRIDGE] Panel closed and the Bridge stopped. "
                    "Nothing is listening now.\n"
                    "   Run the macro again to start over.\n\n")
        except BaseException as exc:
            try:
                App.Console.PrintWarning(
                    "[BRIDGE] Could not stop monitoring on close: "
                    "%s\n" % exc)
            except BaseException:
                pass
        try:
            if FreeCAD.__dict__.get("_ai_bridge_dialog") is self:
                FreeCAD.__dict__["_ai_bridge_dialog"] = None
        except BaseException:
            pass
        super(AIAgentConfigDialog, self).closeEvent(event)

def show_ai_config_gui():
    """Show the AI Agent configuration GUI (non-modal)"""
    if QtWidgets is None:
        App.Console.PrintError("Qt not available - cannot show GUI\n")
        return None
    
    try:
        # v4.0.04: close any panel left open by an earlier run, so the
        # operator is never looking at two control panels driving two
        # different sets of globals.
        try:
            prev = FreeCAD.__dict__.get('_ai_bridge_dialog')
            if prev is not None:
                prev.close()
        except BaseException:
            pass
        dialog = AIAgentConfigDialog(Gui.getMainWindow())
        FreeCAD.__dict__['_ai_bridge_dialog'] = dialog
        dialog.show()  # Non-modal - allows interaction with FreeCAD
        return dialog
    except Exception as e:
        App.Console.PrintError(f"Error showing GUI: {str(e)}\n")
        return None

# ============================================================
# UTILITY FUNCTIONS
# ============================================================

def get_ai_monitoring_status():
    """Get current monitoring status"""
    stats = _state.get_stats()
    
    App.Console.PrintMessage("\n" + "="*70 + "\n")
    App.Console.PrintMessage(f"[AI BRIDGE v{Config.VERSION} STATUS]\n")
    App.Console.PrintMessage("="*70 + "\n\n")
    
    for key, value in stats.items():
        App.Console.PrintMessage(f"{key}: {value}\n")
    
    App.Console.PrintMessage("\n" + "="*70 + "\n\n")
    
    return stats

def show_learning_stats():
    """Display learning system statistics"""
    stats = _learning_system.get_stats()
    
    App.Console.PrintMessage("\n" + "="*70 + "\n")
    App.Console.PrintMessage("[LEARNING SYSTEM STATISTICS]\n")
    App.Console.PrintMessage("="*70 + "\n\n")
    
    for key, value in stats.items():
        App.Console.PrintMessage(f"{key}: {value}\n")
    
    App.Console.PrintMessage("\n" + "="*70 + "\n\n")

def auto_start_monitoring():
    """Auto-start monitoring if not already active"""
    if not _state.monitoring_active:
        return start_ai_monitoring()
    return True

def test_command_processing():
    """Manual test function - callable from console"""
    App.Console.PrintMessage("\n[TEST] Manual command processing test...\n")
    try:
        process_ai_commands_with_recovery()
        App.Console.PrintMessage("[OK] Command processing executed\n")
        stats = _state.get_stats()
        App.Console.PrintMessage(f"Commands processed: {stats['commands_processed']}\n")
        return True
    except Exception as e:
        App.Console.PrintError(f"[ERROR]: {e}\n")
        return False

def get_ai_file_paths():
    """
    Get the correct AI Bridge file paths for external tools (AI assistants, scripts, etc.)
    
    Returns:
        Dictionary with all required file paths
    
    Example usage for AI assistants:
        # In PowerShell, get the correct input file path:
        paths = get_ai_file_paths()
        input_file = paths['input_file']
        
        # Then send commands to that file:
        Add-Content -Path $input_file -Value $json_command
    """
    return {
        'input_file': AI_INPUT_FILE,
        'output_file': AI_OUTPUT_FILE,
        'status_file': AI_STATUS_FILE,
        'health_file': HEALTH_CHECK_FILE,
        'error_log': ERROR_LOG_FILE,
        'learning_db': LEARNING_DB_FILE,
        'io_directory': AI_IO_DIR,
        'learning_directory': LEARNING_DIR
    }

def print_ai_file_paths():
    """Print the correct AI Bridge file paths to console"""
    App.Console.PrintMessage("\n" + "="*70 + "\n")
    App.Console.PrintMessage("[AI BRIDGE FILE PATHS - USE THESE FOR COMMUNICATION]\n")
    App.Console.PrintMessage("="*70 + "\n\n")
    
    paths = get_ai_file_paths()
    App.Console.PrintMessage("📂 I/O Directory:\n")
    App.Console.PrintMessage(f"   {paths['io_directory']}\n\n")
    
    App.Console.PrintMessage("📝 Command Files:\n")
    App.Console.PrintMessage(f"   INPUT (send commands):  {paths['input_file']}\n")
    App.Console.PrintMessage(f"   OUTPUT (read results): {paths['output_file']}\n\n")
    
    App.Console.PrintMessage("Status Files:\n")
    App.Console.PrintMessage(f"   STATUS: {paths['status_file']}\n")
    App.Console.PrintMessage(f"   HEALTH: {paths['health_file']}\n\n")
    
    App.Console.PrintMessage("Learning System:\n")
    App.Console.PrintMessage(f"   DATABASE: {paths['learning_db']}\n")
    App.Console.PrintMessage(f"   DIRECTORY: {paths['learning_directory']}\n\n")
    
    App.Console.PrintMessage("="*70 + "\n\n")
    App.Console.PrintMessage(
        "IMPORTANT: do not use the example I/O files that ship "
        "beside the macro -- the live ones are listed above.\n")
    App.Console.PrintMessage("    Those are templates/examples, not the active communication files!\n\n")
    
    return paths

# ============================================================
# GRACEFUL SHUTDOWN
# ============================================================

def cleanup_on_exit():
    """Cleanup before FreeCAD exits"""
    if _state.monitoring_active:
        App.Console.PrintMessage("AI Bridge shutting down...\n")
        stop_ai_monitoring()

# Register cleanup
atexit.register(cleanup_on_exit)

# ============================================================
# MAIN EXECUTION
# ============================================================

if __name__ == '__main__':
    import warnings
    warnings.filterwarnings('ignore')
    
    # Make key functions globally accessible in FreeCAD console
    import FreeCAD
    # ----------------------------------------------------------------
    # v4.0.04: retire any earlier instance BEFORE publishing our handles.
    #
    # start_ai_monitoring() guards on _state.monitoring_active, a global of
    # ONE macro namespace. FreeCAD gives every run a fresh namespace, so
    # that guard cannot see an earlier run -- and the line below used to
    # overwrite the only handle anyone had to it, stranding its timers for
    # the life of the session. FreeCAD.__dict__ is the one thing both
    # instances can see, so the handover happens here.
    # ----------------------------------------------------------------
    try:
        _prev_stop = FreeCAD.__dict__.get('stop_ai_monitoring')
        if _prev_stop is not None and _prev_stop is not stop_ai_monitoring:
            if bool(_prev_stop()):
                App.Console.PrintWarning(
                    "[BRIDGE] An earlier AI Bridge was still running in "
                    "this FreeCAD session. It has been stopped, so this one "
                    "replaces it rather than polling the same files "
                    "alongside it.\n")
            _prev_dlg = FreeCAD.__dict__.get('_ai_bridge_dialog')
            if _prev_dlg is not None:
                try:
                    _prev_dlg.close()
                except BaseException:
                    pass
                FreeCAD.__dict__['_ai_bridge_dialog'] = None
    except BaseException as _exc:
        App.Console.PrintWarning(
            "[BRIDGE] Could not retire the previous instance: %s\n"
            "   Two Bridges may now be polling the same files. Restart "
            "FreeCAD if commands start going missing.\n" % _exc)

    FreeCAD.__dict__['test_command_processing'] = test_command_processing
    FreeCAD.__dict__['start_ai_monitoring'] = start_ai_monitoring
    FreeCAD.__dict__['stop_ai_monitoring'] = stop_ai_monitoring
    FreeCAD.__dict__['show_ai_config_gui'] = show_ai_config_gui
    FreeCAD.__dict__['get_ai_file_paths'] = get_ai_file_paths
    FreeCAD.__dict__['print_ai_file_paths'] = print_ai_file_paths
    
    if _quiet_mode:
        # QUIET MODE: Auto-start with minimal output
        print("\n" + "="*70)
        print(f"[IMAGINEERING FREECAD AI BRIDGE v{Config.VERSION} - Multi-IDE Bridge]")
        print("="*70 + "\n")
        App.Console.PrintMessage("\n" + "="*70 + "\n")
        App.Console.PrintMessage(f"[IMAGINEERING FREECAD AI BRIDGE v{Config.VERSION} - Multi-IDE Bridge]\n")
        App.Console.PrintMessage("="*70 + "\n\n")

        # Report detected IDEs
        detected_ides = IDEManager.detect_installed_ides()
        if detected_ides:
            ide_names = [info['name'] for info in detected_ides.values()]
            App.Console.PrintMessage(f"[IDEs Detected]: {', '.join(ide_names)}\n")
        else:
            App.Console.PrintMessage("[IDEs]: No supported IDEs detected (VS Code, Windsurf, Cursor, Zed)\n")
        App.Console.PrintMessage("[Tip]: Use the GUI IDE selector to connect to any supported IDE\n\n")
        App.Console.PrintMessage("[Security]: Sandboxed command execution\n")
        App.Console.PrintMessage("[Reliability]: Automatic crash recovery\n")
        App.Console.PrintMessage("[Performance]: Smart polling optimization\n")
        App.Console.PrintMessage("[Persistence]: Auto-save every 5 seconds\n\n")
        
        # Enable logging silently
        param_group = App.ParamGet("User parameter:BaseApp/Preferences/OutputWindow")
        if not param_group.GetBool("RecordLog", False):
            param_group.SetBool("RedirectPythonStdout", True)
            param_group.SetBool("RedirectPythonStderr", True)
            param_group.SetBool("RecordLog", True)
            log_file = os.path.join(App.getUserAppDataDir(), "FreeCAD_Console.log")
            param_group.SetString("LoggingFile", log_file)
            App.Console.PrintMessage("[OK] Console logging enabled\n")
        
        # Initialize I/O directories (but do NOT start monitoring yet)
        setup_ai_io_directory()

        # SELF-LEARNING: Load Technical Data
        try:
            _tech_reviewer = TechDataReviewer()
            if _tech_reviewer.load_all_technical_data():
                App.Console.PrintMessage("[SELF-LEARNING] ✓ Technical knowledge loaded\n")

                # Initialize self-healing system
                if _learning_system:
                    _self_healing = SelfHealingSystem(_learning_system)
                    App.Console.PrintMessage("[SELF-HEALING] ✓ System initialized\n")

                    # Run initial health check
                    if _self_healing.run_health_check():
                        App.Console.PrintMessage("[SELF-HEALING] ✓ All systems healthy\n\n")
                    else:
                        App.Console.PrintWarning(f"[SELF-HEALING] ⚠ {len(_self_healing.issues_detected)} issues detected and fixed\n\n")

        except Exception as e:
            App.Console.PrintWarning(f"[SELF-LEARNING] Could not initialize: {e}\n\n")

        # DO NOT auto-start monitoring - wait for operator to select IDE and click Connect
        App.Console.PrintMessage("\n[WAITING] Select your IDE and click Connect in the Control Panel\n")
        App.Console.PrintMessage("   Monitoring will start when you connect to an IDE.\n\n")
        
        App.Console.PrintMessage("="*70 + "\n")
        App.Console.PrintMessage("[Opening Control Panel]...\n")
        App.Console.PrintMessage("="*70 + "\n\n")
        
        # Auto-launch GUI
        try:
            QtCore.QTimer.singleShot(1000, show_ai_config_gui)
        except Exception as e:
            App.Console.PrintWarning(f"Could not auto-launch GUI: {e}. Run show_ai_config_gui() manually.\n")
    
    else:
        # VERBOSE MODE: Show detailed info
        App.Console.PrintMessage(f"\n[AI BRIDGE v{Config.VERSION} - DETAILED INFORMATION]\n")
        App.Console.PrintMessage("="*70 + "\n\n")
        App.Console.PrintMessage("[AVAILABLE FUNCTIONS]:\n")
        App.Console.PrintMessage("  * show_ai_config_gui() - Open control panel\n")
        App.Console.PrintMessage("  * start_ai_monitoring() - Start monitoring\n")
        App.Console.PrintMessage("  * stop_ai_monitoring() - Stop monitoring\n")
        App.Console.PrintMessage("  * get_ai_monitoring_status() - Check status\n")
        App.Console.PrintMessage("  * show_learning_stats() - View learning stats\n")
        App.Console.PrintMessage("  * run_comprehensive_self_test() - Run tests\n")
        App.Console.PrintMessage("  * get_ai_file_paths() - Get correct file paths (returns dict)\n")
        App.Console.PrintMessage("  * print_ai_file_paths() - Display all file paths\n")
        App.Console.PrintMessage("  * show_tech_data_status() - Show technical data status\n")
        App.Console.PrintMessage("  * run_self_healing_check() - Run health check\n")
        App.Console.PrintMessage("  * generate_ai_context_summary() - Generate AI context file\n")
        App.Console.PrintMessage("  * search_tech_knowledge() - Search knowledge base\n")
        App.Console.PrintMessage("  * get_quick_pattern() - Get quick pattern by category\n")
        App.Console.PrintMessage("  * get_self_learning_stats() - View self-learning statistics\n\n")
        App.Console.PrintMessage("="*70 + "\n\n")

# ============================================================
# SELF-LEARNING HELPER FUNCTIONS
# ============================================================

def show_tech_data_status():
    """Display status of loaded technical data"""
    global _tech_reviewer
    
    if not _tech_reviewer:
        App.Console.PrintWarning("[TECH-DATA] System not initialized. Run macro to load.\n")
        return
    
    App.Console.PrintMessage("\n" + "="*70 + "\n")
    App.Console.PrintMessage("TECHNICAL DATA STATUS\n")
    App.Console.PrintMessage("="*70 + "\n\n")
    
    if _tech_reviewer.loaded:
        App.Console.PrintMessage("Status: ✓ LOADED\n\n")
        
        # Knowledge Base
        if _tech_reviewer.knowledge_base:
            kb_meta = _tech_reviewer.knowledge_base.get('metadata', {})
            App.Console.PrintMessage(f"Knowledge Base:\n")
            App.Console.PrintMessage(f"  Version: {kb_meta.get('version', 'Unknown')}\n")
            App.Console.PrintMessage(f"  Patterns: {kb_meta.get('total_patterns', 0)}\n")
            App.Console.PrintMessage(f"  Updated: {kb_meta.get('last_updated', 'Unknown')}\n\n")
        
        # Quick Patterns
        if _tech_reviewer.quick_patterns:
            App.Console.PrintMessage(f"Quick Reference Patterns:\n")
            for category in _tech_reviewer.quick_patterns.keys():
                App.Console.PrintMessage(f"  • {category}\n")
            App.Console.PrintMessage("\n")
        
        # Reference Files
        App.Console.PrintMessage(f"Reference Files:\n")
        App.Console.PrintMessage(f"  Expressions Guide: {len(_tech_reviewer.expressions_guide)} lines\n")
        App.Console.PrintMessage(f"  Python Conventions: {len(_tech_reviewer.python_conventions)} lines\n\n")
        
    else:
        App.Console.PrintWarning("Status: ✗ NOT LOADED\n\n")
    
    App.Console.PrintMessage("="*70 + "\n\n")

def run_self_healing_check():
    """Manually trigger self-healing health check"""
    global _self_healing
    
    if not _self_healing:
        App.Console.PrintWarning("[SELF-HEAL] System not initialized.\n")
        return False
    
    App.Console.PrintMessage("\n[SELF-HEAL] Running comprehensive health check...\n")
    result = _self_healing.run_health_check()
    
    if result:
        App.Console.PrintMessage("[SELF-HEAL] ✓ All systems healthy!\n")
    else:
        App.Console.PrintWarning(f"[SELF-HEAL] ⚠ Issues detected: {len(_self_healing.issues_detected)}\n")
        App.Console.PrintMessage(f"[SELF-HEAL] Auto-fixes applied: {_self_healing.auto_fixes_applied}\n")
    
    App.Console.PrintMessage(f"[SELF-HEAL] Last check: {_self_healing.last_check_time}\n\n")
    return result

def search_tech_knowledge(query):
    """Search technical knowledge base for information"""
    global _tech_reviewer
    
    if not _tech_reviewer or not _tech_reviewer.loaded:
        App.Console.PrintWarning("[TECH-DATA] Knowledge base not loaded.\n")
        return []
    
    results = _tech_reviewer.search_knowledge(query)
    
    if results:
        App.Console.PrintMessage(f"\n[TECH-DATA] Found {len(results)} results for '{query}':\n")
        for i, result in enumerate(results[:10], 1):  # Show first 10
            App.Console.PrintMessage(f"{i}. {result.get('category', 'Unknown')}")
            if 'key' in result:
                App.Console.PrintMessage(f" -> {result['key']}")
            App.Console.PrintMessage("\n")
        App.Console.PrintMessage("\n")
    else:
        App.Console.PrintMessage(f"[TECH-DATA] No results found for '{query}'\n")
    
    return results

def get_quick_pattern(category, operation=None):
    """Get a quick reference pattern from knowledge base"""
    global _tech_reviewer
    
    if not _tech_reviewer or not _tech_reviewer.loaded:
        App.Console.PrintWarning("[TECH-DATA] Knowledge base not loaded.\n")
        return None
    
    if operation:
        pattern = _tech_reviewer.get_pattern(category, operation)
        if pattern:
            App.Console.PrintMessage(f"\n[PATTERN] {category} -> {operation}:\n")
            if isinstance(pattern, dict):
                for key, value in pattern.items():
                    App.Console.PrintMessage(f"  {key}: {value}\n")
            else:
                App.Console.PrintMessage(f"  {pattern}\n")
            App.Console.PrintMessage("\n")
        return pattern
    else:
        # Show all operations in category
        if category in _tech_reviewer.quick_patterns:
            cat_data = _tech_reviewer.quick_patterns[category]
            App.Console.PrintMessage(f"\n[PATTERN] {category} operations:\n")
            for key in cat_data.keys():
                App.Console.PrintMessage(f"  • {key}\n")
            App.Console.PrintMessage("\n")
            return cat_data
        return None

def get_self_learning_stats():
    """Get comprehensive self-learning system statistics"""
    global _tech_reviewer, _self_healing, _learning_system
    
    stats = {
        'tech_data_loaded': _tech_reviewer.loaded if _tech_reviewer else False,
        'self_healing_active': _self_healing is not None,
        'learning_system_active': _learning_system is not None
    }
    
    if _tech_reviewer and _tech_reviewer.loaded:
        stats['knowledge_patterns'] = len(_tech_reviewer.quick_patterns)
        stats['expressions_lines'] = len(_tech_reviewer.expressions_guide)
        stats['conventions_lines'] = len(_tech_reviewer.python_conventions)
    
    if _self_healing:
        stats['last_health_check'] = str(_self_healing.last_check_time) if _self_healing.last_check_time else 'Never'
        stats['auto_fixes_applied'] = _self_healing.auto_fixes_applied
        stats['issues_detected'] = len(_self_healing.issues_detected)
    
    if _learning_system:
        stats['successful_patterns'] = len(_learning_system.db.get('successful_patterns', []))
        stats['error_resolutions'] = len(_learning_system.db.get('error_resolutions', []))
    
    return stats

# Display self-learning status on load
App.Console.PrintMessage(f"\n[AI BRIDGE v{Config.VERSION}] Complete Feedback Loop: Full Knowledge Base Search + Command Corrections\n")
# v4.0.02: this sentence used to occupy a group box of its own on the
# main window, unchanging, for a whole session. Said once, here.
App.Console.PrintMessage(
    "The Bridge captures successful techniques automatically during "
    "each session and feeds them back to future AI agents.\n\n")
